(defun c:pileta()
  (setq osmodo (getvar "osmode"))
  (setvar "osmode" 0)
  (command "erase" "all" "")
  (command "vpoint" "1,-1,1" "")
  (command "ucs" "w")

  (initget "o s c")
  (setq resp (getkword "\nElija el tipo de piscina deseada: olimpica[o] semiolimpica[s] clavado[c]: "))
  (if (= resp "o")
      (pileolimpica))
  (if (= resp "s")
      (pilesemi))
  (if (= resp "c")
      (pileclavado))  

  (command "-layer" "set" "0" "")
  (command "zoom" "e")
  (setvar "osmode" osmodo)
)

(defun pileolimpica ()
  (setq p_in (getpoint "\nIngrese el punto donde crear la pileta: "))
  (setq ancho (getreal "\nIngrese el ancho de los carriles externos (entre 0.5 mts y 2.5 mts): "))
  (while (or (< ancho 0.5) (> ancho 2.5))
    (setq ancho (getreal "\nIngrese el ancho de los carriles externos (entre 0.5 mts y 2.5 mts): ")))
  (setq diametro_separador (getreal "\nIngrese el diametro de los separadores de carriles (entre 0.1 mts y 0.05 mts): "))
  (while (or (> diametro_separador 0.1) (< diametro_separador 0.05))
    (setq diametro_separador (getreal "\nIngrese el diametro de los separadores de carriles (entre 0.1 mts y 0.05 mts): ")))
  (setq ancho_borde (getreal "\nIngrese el ancho del borde de la pileta (entre 0.5 mts y 1 mts): "))
  (while (or (> ancho_borde 1) (< ancho_borde 0.5))
    (setq ancho_borde (getreal "\nIngrese el ancho del borde de la pileta (entre 0.5 mts y 1 mts): ")))
  (setq altura (getreal "\nIngrese la altura del tirador (entre 0.5 mts y 0.75 mts: "))
  (while (or (> altura 0.75) (< altura 0.5))
    (setq altura (getreal "\nIngrese la altura del tirador (entre 0.5 mts y 0.75 mts: ")))

  ;creacion del hueco de la pileta
  (setq ancho_pileta (+ 20 (* 2 ancho)))
  (setq ancho_final (+ ancho_pileta 0.30))
  (command "_color" 4)
  (command "box" p_in "l" 50 ancho_pileta 2.1)
  (setq hueco_pileta (entlast))
  (setq p_in_ext (list (- (NTH 0 p_in) 0.15) (- (NTH 1 p_in) 0.15) (- (NTH 2 p_in) 0.15))) 
  (command "box" p_in_ext "l" 50.30 ancho_final 2.25)
  (command "subtract" (entlast) "" hueco_pileta "")

  ;borde de la pileta
  (command "_color" 8)
  (setq p_aux (list (NTH 0 p_in_ext) (NTH 1 p_in_ext) (+ (NTH 2 p_in_ext) 2.25)))
  (command "box" p_aux "l" (+ 50.30 (- ancho_borde 0.15)) (* (- ancho_borde 0.15) -1) -0.3)
  (setq borde1 (entlast))
  (setq p_aux1 (list (+ (NTH 0 p_aux) 50.30) (NTH 1 p_aux) (NTH 2 p_aux)))
  (command "box" p_aux1 "l" (- ancho_borde 0.15) (+ (- ancho_borde 0.15) ancho_final) -0.3)
  (setq borde2 (entlast))
  (setq p_aux2 (list (NTH 0 p_aux1) (+ (NTH 1 p_aux1) ancho_final) (NTH 2 p_aux1)))
  (command "box" p_aux2 "l" (* (+ 50.30 (- ancho_borde 0.15)) -1) (- ancho_borde 0.15) -0.3)
  (setq borde3 (entlast))
  (setq p_aux3 (list (- (NTH 0 p_aux2) 50.30) (NTH 1 p_aux2) (NTH 2 p_aux2)))
  (command "box" p_aux3 "l" (* (- ancho_borde 0.15) -1) (* (+ (- ancho_borde 0.15) ancho_final) -1) -0.3)
  (setq borde4 (entlast))
  (command "union" borde1 borde2 borde3 borde4 "")
  (command "zoom" "e")

  ;suavisado bordes
  (command "zoom" "e")
  (command "_color" 4)
  (setq p_aux4 (list (NTH 0 p_in) (+ (NTH 1 p_in) (/ ancho_pileta 2)) (NTH 2 p_in)))
  (command "fillet" p_aux4 0.15 "")
  (setq p_aux5 (list (+ (NTH 0 p_in) 25) (NTH 1 p_in) (NTH 2 p_in)))
  (command "fillet" p_aux5 0.15 "")
  (setq p_aux6 (list (+ (NTH 0 p_in) 25) (+ (NTH 1 p_in) ancho_pileta) (NTH 2 p_in)))
  (command "fillet" p_aux6 0.15 "")
  (setq p_aux7 (list (+ (NTH 0 p_in) 50) (+ (NTH 1 p_in) (/ ancho_pileta 2)) (NTH 2 p_in)))
  (command "fillet" p_aux7 0.15 "")

  (setq p_aux8 (list (NTH 0 p_in) (NTH 1 p_in) (+ (NTH 2 p_in) 1)))
  (command "fillet" p_aux8 0.15 "")
  (setq p_aux9 (list (NTH 0 p_in) (+ (NTH 1 p_in) ancho_pileta) (+ (NTH 2 p_in) 1)))
  (command "fillet" p_aux9 0.15 "")
  (setq p_aux10 (list (+ (NTH 0 p_in) 50) (NTH 1 p_in) (+ (NTH 2 p_in) 1)))
  (command "fillet" p_aux10 0.15 "")
  (setq p_aux11 (list (+ (NTH 0 p_in) 50) (+ (NTH 1 p_in) ancho_pileta) (+ (NTH 2 p_in) 1)))
  (command "fillet" p_aux11 0.15 "")
  
  ;marcas de carriles (fondo)
  (command "_color" 250)
  (if (= ancho 2.5);si el ancho es el maximo, agrega las marcas del fondo del carril
    (progn
      (setq punto_marca1 (list (+ (NTH 0 p_in) 2) (+ (NTH 1 p_in) 0.875) (NTH 2 p_in)))
      (setq punto_marca2 (list (+ (NTH 0 punto_marca1) 0.25) (NTH 1 punto_marca1) (NTH 2 punto_marca1)))
      (setq punto_marca3 (list (NTH 0 punto_marca2) (+ (NTH 1 punto_marca2) 0.25) (NTH 2 punto_marca2)))
      (setq punto_marca4 (list (+ (NTH 0 punto_marca3) 45.5) (NTH 1 punto_marca3) (NTH 2 punto_marca3)))
      (setq punto_marca5 (list (NTH 0 punto_marca4) (- (NTH 1 punto_marca4) 0.25) (NTH 2 punto_marca4)))
      (setq punto_marca6 (list (+ (NTH 0 punto_marca5) 0.25) (NTH 1 punto_marca5) (NTH 2 punto_marca5)))
      (setq punto_marca7 (list (NTH 0 punto_marca6) (+ (NTH 1 punto_marca6) 0.75) (NTH 2 punto_marca6)))
      (setq punto_marca8 (list (- (NTH 0 punto_marca7) 0.25) (NTH 1 punto_marca7) (NTH 2 punto_marca7)))
      (setq punto_marca9 (list (NTH 0 punto_marca8) (- (NTH 1 punto_marca8) 0.25) (NTH 2 punto_marca8)))
      (setq punto_marca10 (list (- (NTH 0 punto_marca9) 45.5) (NTH 1 punto_marca9) (NTH 2 punto_marca9)))
      (setq punto_marca11 (list (NTH 0 punto_marca10) (+ (NTH 1 punto_marca10) 0.25) (NTH 2 punto_marca10)))
      (setq punto_marca12 (list (- (NTH 0 punto_marca11) 0.25) (NTH 1 punto_marca11) (NTH 2 punto_marca11)))
      (command "pline" punto_marca1 punto_marca2 punto_marca3 punto_marca4 punto_marca5 punto_marca6 punto_marca7 punto_marca8 punto_marca9 punto_marca10 punto_marca11 punto_marca12 "c")
      (command "extrude" (entlast) "" 0.001 "")
      (command "array" (entlast) "" "r" 10 1 2.5)))
  
  (if (/= ancho 2.5);como el ancho es menor al de los demas carriles, no dibuja la marca del fondo del carril
    (progn
      (setq punto_marca11 (list (+ (NTH 0 p_in) 2) (+ (+ (NTH 1 p_in) 0.875) ancho) (NTH 2 p_in)))
      (setq punto_marca22 (list (+ (NTH 0 punto_marca11) 0.25) (NTH 1 punto_marca11) (NTH 2 punto_marca11)))
      (setq punto_marca33 (list (NTH 0 punto_marca22) (+ (NTH 1 punto_marca22) 0.25) (NTH 2 punto_marca22)))
      (setq punto_marca44 (list (+ (NTH 0 punto_marca33) 45.5) (NTH 1 punto_marca33) (NTH 2 punto_marca33)))
      (setq punto_marca55 (list (NTH 0 punto_marca44) (- (NTH 1 punto_marca44) 0.25) (NTH 2 punto_marca44)))
      (setq punto_marca66 (list (+ (NTH 0 punto_marca55) 0.25) (NTH 1 punto_marca55) (NTH 2 punto_marca55)))
      (setq punto_marca77 (list (NTH 0 punto_marca66) (+ (NTH 1 punto_marca66) 0.75) (NTH 2 punto_marca66)))
      (setq punto_marca88 (list (- (NTH 0 punto_marca77) 0.25) (NTH 1 punto_marca77) (NTH 2 punto_marca77)))
      (setq punto_marca99 (list (NTH 0 punto_marca88) (- (NTH 1 punto_marca88) 0.25) (NTH 2 punto_marca88)))
      (setq punto_marca100 (list (- (NTH 0 punto_marca99) 45.5) (NTH 1 punto_marca99) (NTH 2 punto_marca99)))
      (setq punto_marca111 (list (NTH 0 punto_marca100) (+ (NTH 1 punto_marca100) 0.25) (NTH 2 punto_marca100)))
      (setq punto_marca122 (list (- (NTH 0 punto_marca111) 0.25) (NTH 1 punto_marca111) (NTH 2 punto_marca111)))
      (command "pline" punto_marca11 punto_marca22 punto_marca33 punto_marca44 punto_marca55 punto_marca66 punto_marca77 punto_marca88 punto_marca99 punto_marca100 punto_marca111 punto_marca122 "c")
      (command "extrude" (entlast) "" 0.001 "")
      (command "array" (entlast) "" "r" 8 1 2.5)))

  ;marcas de carriles (pared)
  (if (= ancho 2.5);si el ancho es el maximo, agrega las marcas
    (progn
    (setq pun1 (list (- (NTH 0 punto_marca3) 2.25) (NTH 1 punto_marca3) (NTH 2 punto_marca3)))
    (setq pun2 (list (NTH 0 pun1) (+ (NTH 1 pun1) 0.25) (NTH 2 pun1)))
    (setq pun3 (list (NTH 0 pun2) (NTH 1 pun2) (+ (NTH 2 pun2) 1.375)))
    (setq pun4 (list (NTH 0 pun3) (+ (NTH 1 pun3) 0.25) (NTH 2 pun3)))
    (setq pun5 (list (NTH 0 pun4) (NTH 1 pun4) (+ (NTH 2 pun4) 0.25)))
    (setq pun6 (list (NTH 0 pun5) (- (NTH 1 pun5) 0.25) (NTH 2 pun5)))
    (setq pun7 (list (NTH 0 pun6) (NTH 1 pun6) (+ (NTH 2 pun6) 0.475)))
    (setq pun8 (list (NTH 0 pun7) (- (NTH 1 pun7) 0.25) (NTH 2 pun7)))
    (setq pun9 (list (NTH 0 pun8) (NTH 1 pun8) (- (NTH 2 pun8) 0.475)))
    (setq pun10 (list (NTH 0 pun9) (- (NTH 1 pun9) 0.25) (NTH 2 pun9)))
    (setq pun11 (list (NTH 0 pun10) (NTH 1 pun10) (- (NTH 2 pun10) 0.25)))
    (setq pun12 (list (NTH 0 pun11) (+ (NTH 1 pun11) 0.25) (NTH 2 pun11)))
    (setq pun13 (list (NTH 0 pun12) (NTH 1 pun12) (- (NTH 2 pun12) 1.375)))
    (command "_3dpoly" pun1 pun2 pun3 pun4 pun5 pun6 pun7 pun8 pun9 pun10 pun11 pun12 "c")
    (command "extrude" (entlast) "" 0.001 "")
    (setq prim_form (entlast))
    ;dos puntos para hacer el mirror
    (setq pmirr1 (list (+ (NTH 0 p_in) 25) (NTH 1 p_in) (NTH 2 p_in)))
    (setq pmirr2 (list (+ (NTH 0 p_in) 25) (+ (NTH 1 p_in) ancho_pileta) (NTH 2 p_in)))
    (command "mirror" (entlast) "" pmirr1 pmirr2 "")
    (command "array" prim_form (entlast) "" "r" 10 1 2.5)))

  (if (/= ancho 2.5)
    (progn
    (setq pun1 (list (- (NTH 0 punto_marca33) 2.25) (NTH 1 punto_marca33) (NTH 2 punto_marca33)))
    (setq pun2 (list (NTH 0 pun1) (+ (NTH 1 pun1) 0.25) (NTH 2 pun1)))
    (setq pun3 (list (NTH 0 pun2) (NTH 1 pun2) (+ (NTH 2 pun2) 1.375)))
    (setq pun4 (list (NTH 0 pun3) (+ (NTH 1 pun3) 0.25) (NTH 2 pun3)))
    (setq pun5 (list (NTH 0 pun4) (NTH 1 pun4) (+ (NTH 2 pun4) 0.25)))
    (setq pun6 (list (NTH 0 pun5) (- (NTH 1 pun5) 0.25) (NTH 2 pun5)))
    (setq pun7 (list (NTH 0 pun6) (NTH 1 pun6) (+ (NTH 2 pun6) 0.475)))
    (setq pun8 (list (NTH 0 pun7) (- (NTH 1 pun7) 0.25) (NTH 2 pun7)))
    (setq pun9 (list (NTH 0 pun8) (NTH 1 pun8) (- (NTH 2 pun8) 0.475)))
    (setq pun10 (list (NTH 0 pun9) (- (NTH 1 pun9) 0.25) (NTH 2 pun9)))
    (setq pun11 (list (NTH 0 pun10) (NTH 1 pun10) (- (NTH 2 pun10) 0.25)))
    (setq pun12 (list (NTH 0 pun11) (+ (NTH 1 pun11) 0.25) (NTH 2 pun11)))
    (setq pun13 (list (NTH 0 pun12) (NTH 1 pun12) (- (NTH 2 pun12) 1.375)))
    (command "_3dpoly" pun1 pun2 pun3 pun4 pun5 pun6 pun7 pun8 pun9 pun10 pun11 pun12 "c")
    (command "extrude" (entlast) "" 0.001 "")
    (setq prim_form (entlast))
    ;dos puntos para hacer el mirror
    (setq pmirr1 (list (+ (NTH 0 p_in) 25) (NTH 1 p_in) (NTH 2 p_in)))
    (setq pmirr2 (list (+ (NTH 0 p_in) 25) (+ (NTH 1 p_in) ancho_pileta) (NTH 2 p_in)))
    (command "mirror" (entlast) "" pmirr1 pmirr2 "")
    (command "array" prim_form (entlast) "" "r" 8 1 2.5)))

  ;luces
  (command "_color" 7)
  (setq punto_luz (list (+ (NTH 0 p_in) 10) (- (NTH 1 p_in) 0.025) (+ (NTH 2 p_in) (- 1.8 (* 18 0.0254)))));desde arriba hacia el fondo, 75% de la longitud
  (command "sphere" punto_luz 0.125)
  (setq prim (entlast))
  (setq punmirr1 (list (NTH 0 p_in) (+ (NTH 1 p_in) (/ ancho_pileta 2)) (NTH 2 p_in)))
  (setq punmirr2 (list (+ (NTH 0 punmirr1) 50) (NTH 1 punmirr1) (NTH 2 punmirr1)))
  (command "mirror" (entlast) "" punmirr1 punmirr2 "")
  (command "array" prim (entlast) "" "r" 1 4 10)

  ;banderines
  (command "layer" "m" "nueva2" "" "")
  (command "_color" 7)
  (setq p_in_ban (list (+ (NTH 0 p_in) 5) (- (NTH 1 p_in) (/ ancho_borde 2)) (+ (NTH 2 p_in) 2.1)))
  (setq p_in_ban2 (list (NTH 0 p_in_ban) (+ (NTH 1 p_in_ban) (+ ancho_borde ancho_pileta)) (NTH 2 p_in_ban)))
  (command "cylinder" p_in_ban 0.03 1.8)
  (command "cylinder" p_in_ban2 0.03 1.8)
  (setq p_esf1 (list (NTH 0 p_in_ban) (NTH 1 p_in_ban) (+ (NTH 2 p_in_ban) 1.8)))
  (setq p_esf2 (list (NTH 0 p_in_ban2) (NTH 1 p_in_ban2) (+ (NTH 2 p_in_ban2) 1.8)))
  (command "sphere" p_esf1 0.03)
  (command "sphere" p_esf2 0.03)
  (setq p_fin_ban1 (list (NTH 0 p_in_ban) (NTH 1 p_in_ban) (+ (NTH 2 p_in_ban) 1.7)));como agrego la cuerda de 1 cm de diametro, para no superar el 1.8 mts
  (setq p_fin_ban2 (list (NTH 0 p_in_ban2) (NTH 1 p_in_ban2) (+ (NTH 2 p_in_ban2) 1.7)))
  (setq p_fin_ban3 (list (NTH 0 p_fin_ban2) (NTH 1 p_fin_ban2) (+ (NTH 2 p_fin_ban2) 0.01)))
  (setq p_fin_ban4 (list (NTH 0 p_fin_ban1) (NTH 1 p_fin_ban1) (+ (NTH 2 p_fin_ban1) 0.01)))
  (command "_color" 7)
  (command "3dpoly" p_fin_ban1 p_fin_ban2 p_fin_ban3 p_fin_ban4 "c")
  (command "revolve" (entlast) "" p_fin_ban1 p_fin_ban2 "")
  (setq tamband (/ (/ (* ancho_pileta 100) 50) 100))
  (command "_color" 2)
  (setq p_triang1 (list (NTH 0 p_in_ban) (+ (NTH 1 p_in_ban) (/ ancho_borde 2)) (+ (NTH 2 p_in_ban) 1.7)))
  (setq p_triang2 (list (NTH 0 p_triang1) (+ (NTH 1 p_triang1) (/ tamband 2)) (- (NTH 2 p_triang1) tamband)))
  (setq p_triang3 (list (NTH 0 p_triang1) (+ (NTH 1 p_triang1) tamband) (NTH 2 p_triang1)))
  (command "3dpoly" p_triang1 p_triang2 p_triang3 "c")
  (command "extrude" (entlast) "" 0.001 "")
  (command "array" (entlast) "" "r" 50 1 tamband)
  (setq enti (ssget "x" '((8 . "nueva2"))))
  (command "mirror" enti "" pmirr1 pmirr2 "")
  (command "-layer" "set" "0" "")

  ;tirador
  ;la altura de la inclinacion es c, inclinacion gama y la base es a. tang gama = c/a, de ahi despejo la altura
  ;para piletas olimpicas, gama es 10°
  ;0.5 es el tamaño de lado de la plataforma
  ;la distancia desde el borde hacia donde se coloca el tirador es tal que el borde del tirador este justo encima del borde de la pileta
  (command "_color" 250)
  (command "-layer" "set" "0" "")
  (if (= ancho 2.5)
    (progn
      (setq pun_tir (list (- (NTH 0 p_in) 0.25) (+ (NTH 1 p_in) 1) (+ (+ (NTH 2 p_in) 2.1) altura)))
      (setq angulo_rad (/ (* 10 (* 2 pi)) 360))
      (setq altura_inclinacion (* (/ (sin angulo_rad)(cos angulo_rad)) 0.5))
      (command "box" pun_tir "l" 0.5 0.5 (/ (* 25 altura) 100))
      (setq box_inf (entlast))
      (setq punto_aux (list (NTH 0 pun_tir) (NTH 1 pun_tir) (+ (NTH 2 pun_tir) (/ (* 25 altura) 100))))
      (command "wedge" punto_aux "l" 0.5 0.5 altura_inclinacion)
      (setq box_sup (entlast))
      (setq punto_aux (list (+ (NTH 0 pun_tir) 0.25) (+ (NTH 1 pun_tir) 0.25) (NTH 2 pun_tir)))
      (command "cylinder" punto_aux 0.1 (* (- altura 0.3) -1))
      (command "union" box_inf box_sup (entlast) "")
      (command "array" (entlast) "" "r" 10 1 2.5)))

  (if (/= ancho 2.5)
    (progn
      (setq pun_tir (list (- (NTH 0 p_in) 0.25) (+ (NTH 1 p_in) (+ 1 ancho)) (+ (+ (NTH 2 p_in) 2.1) altura)))
      (setq angulo_rad (/ (* 10 (* 2 pi)) 360))
      (setq altura_inclinacion (* (/ (sin angulo_rad)(cos angulo_rad)) 0.5))
      (command "box" pun_tir "l" 0.5 0.5 (/ (* 25 altura) 100))
      (setq box_inf (entlast))
      (setq punto_aux (list (NTH 0 pun_tir) (NTH 1 pun_tir) (+ (NTH 2 pun_tir) (/ (* 25 altura) 100))))
      (command "wedge" punto_aux "l" 0.5 0.5 altura_inclinacion)
      (setq box_sup (entlast))
      (setq punto_aux (list (+ (NTH 0 pun_tir) 0.25) (+ (NTH 1 pun_tir) 0.25) (NTH 2 pun_tir)))
      (command "cylinder" punto_aux 0.1 (* (- altura 0.3) -1))
      (command "union" box_inf box_sup (entlast) "")
      (command "array" (entlast) "" "r" 8 1 2.5)))
  
  (command "-layer" "set" "0" "")
  (command "union" "all" "")
  (command "regen")
  (command "purge" "all" "" "n")
  (command "hide")

  ;seeparadores
  (command "layer" "m" "nueva" "" "")
  (command "_color" 250)
  (setq radio_sep (/ diametro_separador 2))
  (setq numbloc1 (fix (/ 5 diametro_separador))
	numbloc2 (fix (/ 40 diametro_separador)))
  (setq pun_separador1 (list (+ (NTH 0 p_in) radio_sep) (+ (NTH 1 p_in) ancho) (+ (NTH 2 p_in) 1.7)))
  (setq p_sep_1 (list (- (NTH 0 pun_separador1) radio_sep) (NTH 1 pun_separador1) (- (NTH 2 pun_separador1) 0.01)));como agrego la cuerda de 1 cm de diametro, para no superar el 1.8 mts
  (setq p_sep_2 (list (+ (NTH 0 p_sep_1) 50) (NTH 1 p_sep_1) (NTH 2 p_sep_1)))
  (setq p_sep_3 (list (NTH 0 p_sep_2) (NTH 1 p_sep_2) (+ (NTH 2 p_sep_2) 0.02)))
  (setq p_sep_4 (list (NTH 0 p_sep_1) (NTH 1 p_sep_1) (+ (NTH 2 p_sep_1) 0.02)))
  (command "3dpoly" p_sep_1 p_sep_2 p_sep_3 p_sep_4 "c")
  (command "revolve" (entlast) "" p_sep_1 p_sep_2 "")
  (command "_color" 2)
  (command "sphere" pun_separador1 radio_sep)
  (command "array" (entlast) "" "r" 1 numbloc1 diametro_separador)
  (setq pun_separador2 (list (+ (NTH 0 pun_separador1) 5) (NTH 1 pun_separador1) (NTH 2 pun_separador1)))
  (command "_color" 1)
  (command "sphere" pun_separador2 radio_sep)
  (command "array" (entlast) "" "r" 1 numbloc2 diametro_separador)
  (setq pun_separador3 (list (+ (NTH 0 pun_separador2) 40) (NTH 1 pun_separador2) (NTH 2 pun_separador2)))
  (command "_color" 2)
  (command "sphere" pun_separador3 radio_sep)
  (command "array" (entlast) "" "r" 1 numbloc1 diametro_separador)
  (setq enti (ssget "x" '((8 . "nueva"))))
  (command "array" enti "" "r" 9 1 2.5)
  (setq enti1 (ssget "x" '((8 . "nueva"))))
  (command "change" enti1 "" "p" "la" "0" "")
  
  (command "-layer" "set" "0" "")
  ;(command "union" "all" "")
  ;(command "regen")
  (command "purge" "all" "" "n")
  (command "hide")
)

(defun pileclavado()
  (setq p_in (getpoint "\nIngrese el punto donde crear la pileta: "))
  (setq lado (getreal "\nIngrese el tamaño de los lados (entre 13 mts y 20 mts): "))
  (while (or (< lado 13) (> lado 20))
    (setq lado (getreal "\nIngrese el ancho de los carriles (entre 13 mts y 20 mts): ")))
  (setq diametro_separador (getreal "\nIngrese el diametro de los separadores de carriles (entre 0.1 mts y 0.05 mts): "))
  (while (or (> diametro_separador 0.1) (< diametro_separador 0.05))
    (setq diametro_separador (getreal "\nIngrese el diametro de los separadores de carriles (entre 0.1 mts y 0.05 mts): ")))
  (setq ancho_borde (getreal "\nIngrese el ancho del borde de la pileta (entre 0.5 mts y 1 mts): "))
  (while (or (> ancho_borde 1) (< ancho_borde 0.5))
    (setq ancho_borde (getreal "\nIngrese el ancho del borde de la pileta (entre 0.5 mts y 1 mts): ")))
  (if (>= lado 17)
    (progn
      (initget "si no")
      (setq resp (getkword "\nDesea Agregar trampolines extra?: [si] [no]: "))))
  (if (<= lado 16)
    (progn
      (setq resp "no")))
  (setq num_tram (getint "\nIngrese el numero de trampolines (1 - 2 - 3 - 4): "))
  (while (or (> num_tram 4) (< num_tram 1))
    (setq num_tram (getreal "\nIngrese el numero de trampolines (1 - 2 - 3 - 4): ")))
  
  ;no solicito la profundidad de la pileta ya que esta medida depende del numero de trampolines que tenga
  (if (= num_tram 1);profundidad= 3 mts; tramp = 3 mts
    (progn
      ;creacion del hueco de la pileta
      (setq prof 3)
      (command "_color" 4)
      (command "box" p_in "l" lado lado prof)
      (setq hueco_pileta (entlast))
      (setq p_in_ext (list (- (NTH 0 p_in) 0.15) (- (NTH 1 p_in) 0.15) (- (NTH 2 p_in) 0.15)))
      (command "_color" 8)
      (command "box" p_in_ext "l" (+ lado 0.30) (+ lado 0.30) (+ prof 0.15))
      (command "subtract" (entlast) "" hueco_pileta "")

      ;borde de la pileta
      (command "_color" 8)
      (setq p_aux (list (NTH 0 p_in_ext) (NTH 1 p_in_ext) (+ (NTH 2 p_in_ext) (+ prof 0.15))))
      (command "box" p_aux "l" (+ (+ lado 0.30) (- ancho_borde 0.15)) (* (- ancho_borde 0.15) -1) -0.3)
      (setq borde1 (entlast))
      (setq p_aux1 (list (+ (NTH 0 p_aux) (+ lado 0.30)) (NTH 1 p_aux) (NTH 2 p_aux)))
      (command "box" p_aux1 "l" (- ancho_borde 0.15) (+ (- ancho_borde 0.15) (+ lado 0.30)) -0.3)
      (setq borde2 (entlast))
      (setq p_aux2 (list (NTH 0 p_aux1) (+ (NTH 1 p_aux1) (+ lado 0.30)) (NTH 2 p_aux1)))
      (command "box" p_aux2 "l" (* (+ (+ lado 0.30) (- ancho_borde 0.15)) -1) (- ancho_borde 0.15) -0.3)
      (setq borde3 (entlast))
      (setq p_aux3 (list (- (NTH 0 p_aux2) (+ lado 0.30)) (NTH 1 p_aux2) (NTH 2 p_aux2)))
      (command "box" p_aux3 "l" (* (- ancho_borde 0.15) -1) (* (+ (- ancho_borde 0.15) (+ lado 0.30)) -1) -0.3)
      (setq borde4 (entlast))
      (command "union" borde1 borde2 borde3 borde4 "")
      (setq p_p_aux (list (NTH 0 p_aux) (+ (- (NTH 1 p_aux) ancho_borde) 0.15) (NTH 2 p_aux)))
      (command "box" p_p_aux "l" -6 (+ (* ancho_borde 2) lado) -0.3)
      (command "zoom" "e")

      ;suavisado bordes
      (command "zoom" "e")
      (command "_color" 4)
      (setq p_aux4 (list (NTH 0 p_in) (+ (NTH 1 p_in) (/ lado 2)) (NTH 2 p_in)))
      (command "fillet" p_aux4 0.15 "")
      (setq p_aux5 (list (+ (NTH 0 p_in) (/ lado 2)) (NTH 1 p_in) (NTH 2 p_in)))
      (command "fillet" p_aux5 0.15 "")
      (setq p_aux6 (list (+ (NTH 0 p_in) (/ lado 2)) (+ (NTH 1 p_in) lado) (NTH 2 p_in)))
      (command "fillet" p_aux6 0.15 "")
      (setq p_aux7 (list (+ (NTH 0 p_in) lado) (+ (NTH 1 p_in) (/ lado 2)) (NTH 2 p_in)))
      (command "fillet" p_aux7 0.15 "")

      (setq p_aux8 (list (NTH 0 p_in) (NTH 1 p_in) (+ (NTH 2 p_in) 1)))
      (command "fillet" p_aux8 0.15 "")
      (setq p_aux9 (list (NTH 0 p_in) (+ (NTH 1 p_in) lado) (+ (NTH 2 p_in) 1)))
      (command "fillet" p_aux9 0.15 "")
      (setq p_aux10 (list (+ (NTH 0 p_in) lado) (NTH 1 p_in) (+ (NTH 2 p_in) 1)))
      (command "fillet" p_aux10 0.15 "")
      (setq p_aux11 (list (+ (NTH 0 p_in) lado) (+ (NTH 1 p_in) lado) (+ (NTH 2 p_in) 1)))
      (command "fillet" p_aux11 0.15 "")

      ;trampolin
      (command "_color" 8)
      (setq alt 3)
      (if (= resp "si")
	(progn
	  (setq pbox (list (- (NTH 0 p_in) 2.5) (- (+ (NTH 1 p_in) (/ (/ lado 2) 2)) 0.5625) (+ (NTH 2 p_in) prof)))));desde este punto al agua hay 2.25 mts por regla, como ancho del box recto, tomo la mitad de esta distancia
      (if (= resp "no")
	(progn
	  (setq pbox (list (- (NTH 0 p_in) 2.5) (- (+ (NTH 1 p_in) (/ lado 2)) 0.5625) (+ (NTH 2 p_in) prof)))))
      (command "box" pbox "l" 1.125 1.125 alt)
      (command "wedge" pbox "l" -2.59 1.125 alt)
      (setq p_sop (list (NTH 0 pbox) (- (NTH 1 pbox) 0.8125) (+ (NTH 2 pbox) (- alt 0.25))));el ancho maximo de la plataforma es 75 cm
      (command "_color" 7)
      (command "wedge" p_sop "l" 4.3 2.75 -0.50)
      (command "wedge" p_sop "l" -2.59 2.75 -0.50)
      (command "box" p_sop "l" 4.3 2.75 0.25)
      (command "box" p_sop "l" -2.59 2.75 0.25)
      (setq p_escalera1 (list (- (NTH 0 p_sop) 2.4) (+ (NTH 1 p_sop) 2.75) (+ (NTH 2 p_sop) 0.25)))
      (setq p_escalera2 (list (+ (NTH 0 p_escalera1) 0.5) (NTH 1 p_escalera1) (NTH 2 p_escalera1)))
      (command "cylinder" p_escalera1 0.05 (* alt -1))
      (command "cylinder" p_escalera2 0.05 (* alt -1))
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" (- (/ (* alt 100) 25) 1) 1 -0.25)
      (command "ucs" "w")

      ;barandas
      (setq p_baranda1 (list (NTH 0 p_sop) (+ (NTH 1 p_sop) 0.05) (+ (NTH 2 p_sop) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq seg_cil (entlast))
      (setq punmirr1 (list (NTH 0 p_sop) (+ (NTH 1 p_sop) 1.375) (NTH 2 p_sop)))
      (setq punmirr2 (list (- (NTH 0 punmirr1) 2.59) (NTH 1 punmirr1) (NTH 2 punmirr1)))
      (command "mirror" prim_cil seg_cil "" punmirr1 punmirr2 "")
      
      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (+ (NTH 1 p_baranda1) 2.65) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;tramp_extras
      (if (= resp "si")
	(progn
	  (setq pbox (list (- (NTH 0 p_in) 2.5) (- (+ (NTH 1 p_in) (- lado (/ (/ lado 2) 2))) 2.5) (+ (NTH 2 p_in) prof)))
	  (command "box" pbox "l" 2.5 6 0.75)
	  (setq pboxaux (list (NTH 0 pbox) (+ (NTH 1 pbox) 0.1) (NTH 2 pbox)))
	  (command "layer" "m" "tramp_chico" "" "")
	  (command "box" pboxaux "l" -0.25 0.5 0.5)
	  (setq pbox2 (list (- (NTH 0 pboxaux) 0.25) (NTH 1 pboxaux) (NTH 2 pboxaux)))
	  (command "box" pbox2 "l" -0.25 0.5 0.25)
	  (setq pbar1 (list (+ (NTH 0 pbox) 0.05) (+ (NTH 1 pbox) 0.05) (+ (NTH 2 pbox) 0.75)))
	  (setq pbar2 (list (+ (NTH 0 pbar1) 2.4) (NTH 1 pbar1) (NTH 2 pbar1)))
	  (command "cylinder" pbar1 0.05 1)
	  (command "cylinder" pbar2 0.05 1)
	  (setq p1 (list (NTH 0 pbar1) (NTH 1 pbar1) (+ (NTH 2 pbar1) 0.95)))
	  (setq p2 (list (NTH 0 pbar2) (NTH 1 pbar2) (+ (NTH 2 pbar2) 0.95)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_cil1 (list (+ (NTH 0 pbox) 1.3) (+ (NTH 1 pbox) 1.2) (+ (NTH 2 pbox) 0.75)))
	  (setq p_cil2 (list (NTH 0 p_cil1) (+ (NTH 1 p_cil1) 0.6) (NTH 2 p_cil1)))
	  (command "cylinder" p_cil1 0.05 0.15)
	  (command "cylinder" p_cil2 0.05 0.15)
	  (setq p_circ1 (list (NTH 0 p_cil1) (NTH 1 p_cil1) (+ (NTH 2 p_cil1) 0.15)))
	  (setq p_circ2 (list (NTH 0 p_cil2) (NTH 1 p_cil2) (+ (NTH 2 p_cil2) 0.15)))
	  (command "circle" p_circ1 0.05)
	  (setq cir1 (entlast))
	  (command "circle" p_circ2 0.05)
	  (setq cir2 (entlast))
	  (setq p_rev1 (list (NTH 0 p_circ1) (+ (NTH 1 p_circ1) 0.05) (NTH 2 p_circ1)))
	  (setq p_rev2 (list (- (NTH 0 p_rev1) 0.1) (NTH 1 p_rev1) (NTH 2 p_rev1)))
	  (setq p_rev11 (list (NTH 0 p_circ2) (- (NTH 1 p_circ2) 0.05) (NTH 2 p_circ2)))
	  (setq p_rev22 (list (- (NTH 0 p_rev11) 0.1) (NTH 1 p_rev11) (NTH 2 p_rev11)))
	  (command "revolve" cir1 "" p_rev1 p_rev2 90)
	  (command "revolve" cir2 "" p_rev11 p_rev22 -90)
	  (setq p1 (list (NTH 0 p_cil1) (+ (NTH 1 p_cil1) 0.05) (+ (NTH 2 p_cil1) 0.2)))
	  (setq p2 (list (NTH 0 p1) (+ (NTH 1 p1) 0.5) (NTH 2 p1)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_tramp (list (NTH 0 p1) (NTH 1 p1) (+ (NTH 2 p1) 0.05)))
	  (command "box" p_tramp "l" 3 0.5 0.05)
	  (setq p_boxtramp (list (+ (NTH 0 p_tramp) 0.6) (+ (NTH 1 p_tramp) 0.05) (NTH 2 p_tramp)))
	  (command "box" p_boxtramp "l" 0.4 0.4 -0.25)
	  (setq pmirr1 (list (+ (NTH 0 pbox) 2.5) (+ (NTH 1 pbox) 3) (+ (NTH 2 pbox) 0.75)))
	  (setq pmirr2 (list (- (NTH 0 pmirr1) 2.5) (NTH 1 pmirr1) (NTH 2 pmirr1)))
	  (setq enti (ssget "x" '((8 . "tramp_chico"))))
	  (command "mirror" enti "" pmirr1 pmirr2 "")
	  (setq enti1 (ssget "x" '((8 . "tramp_chico"))))
	  (command "change" enti1 "" "p" "la" "0" "")
	  (command "-layer" "set" "0" "")
	  )
	)

      ;ESCALERAS
      (command "-layer" "n" "escaleras" "set" "escaleras" "")
      (command "ucs" "w")
      ;definir punto de inicio escalera
      (setq p0 (list (+ (nth 0 p_in) 0.3) (+ (nth 1 p_in) (+ lado 0.3)) (+ (nth 2 p_in) prof)));punto inicio de la escalera
      ;cilindro 1
      (command "cylinder" p0 0.02 0.45)
      (setq cilindro1 (entlast))
      ;cilindro curvo 1
      (command "zoom" "e")
      (setq p1 (list (nth 0 p0) (nth 1 p0) (+(nth 2 p0)0.45) ))
      (command "circle" p1 0.02 "")
      (setq circulo1 (entlast))
      (setq p1Eje (list (nth 0 p1) (- (nth 1 p1) 0.3) (nth 2 p1) ))
      (setq p2Eje (list (- (nth 0 p1) 0.3) (- (nth 1 p1) 0.3) (nth 2 p1)))
      (command "revolve" circulo1 "" p1Eje p2Eje -180 "")
      (setq cilindroCurvo (entlast))
      ;cilindro 2
      (setq p2 (list (nth 0 p1) (-(nth 1 p1)0.60) (nth 2 p1)))
      (command "cylinder" p2 0.02 -1.45)
      (setq cilindro2 (entlast))
      ;cilindro curvo 2
      (setq p3 (list (nth 0 p2) (nth 1 p2) (-(nth 2 p2) 1.45)))
      (command "circle" p3 0.02 "")
      (setq circulo2 (entlast))
      (setq p1Eje2 (list (nth 0 p3) (+ (nth 1 p3) 0.3) (nth 2 p3)))
      (setq p2Eje2 (list (+ (nth 0 p3) 0.3) (+ (nth 1 p3) 0.3) (nth 2 p3)))
      (command "revolve" circulo2 "" p1Eje2 p2Eje2 90 "")
      (setq cilindroCurvo2 (entlast))
      (command "union"  cilindro1 cilindroCurvo cilindro2 cilindroCurvo2 "")
      (setq canio1 (entlast))
      ;caño dos
      (setq p0Canio2 (list (+ (nth 0 p0) 0.5) (nth 1 p0)(nth 2 p0)))
      (command "copy" canio1 "" p0  p0Canio2)
      ;escalones
      (setq p1Escalon (list (nth 0 p2) (-(nth 1 p2) 0.075) (-(nth 2 p2)0.65)));
      (command "box" p1Escalon "l" 0.5 0.15 -0.03)
      (setq escalon (entlast))
      (command "ucs" "x" 90)
      (command "array" escalon "" "r" 4 1 -0.25)
      (command "ucs" "w")
      (command "-layer" "set" "escaleras" "")
      (setq escaleraTodo (ssget "x" '((8 . "escaleras"))))
      (command "union" escaleraTodo "" )
      (setq escComp (entlast));escalera
      ;escalera 2
      (command "zoom" "e")
      (setq mir1 (list (+ (NTH 0 p_in) (/ lado 2)) (NTH 1 p_in) (NTH 2 p_in)))
      (setq mir2 (list (NTH 0 mir1) (+ (NTH 1 mir1) lado) (NTH 2 mir1)))
      (command "mirror" escComp "" mir1 mir2 "")
      (setq escComp2 (entlast))
      ;miror
      (setq mi1l (list (+ (NTH 0 p_in) lado) (+ (NTH 1 p_in) (/ lado 2)) (NTH 2 p_in)))
      (setq mi2l (list (- (NTH 0 mi1l) lado) (NTH 1 mi1l) (NTH 2 mi1l)))
      (command "mirror" escComp escComp2 "" mi1l mi2l "")
      (setq enti1 (ssget "x" '((8 . "escaleras"))))
      (command "change" enti1 "" "p" "la" "0" "")
      (command "-layer" "set" "0" "")

      ;seeparador
      (command "layer" "m" "nueva" "" "")
      (setq radio_sep (/ diametro_separador 2))
      (setq numbloc1 (fix (/ (/ lado 4) diametro_separador))
	    numbloc2 (fix (/ (/ lado 2) diametro_separador)))
      (setq pun_separador1 (list (+ (NTH 0 p_in) (/ (* lado 80) 100)) (+ (NTH 1 p_in) radio_sep) (+ (NTH 2 p_in) (- prof 0.1))))
      (setq p_sep_1 (list (NTH 0 pun_separador1) (- (NTH 1 pun_separador1) radio_sep) (- (NTH 2 pun_separador1) 0.01)))
      (setq p_sep_2 (list (NTH 0 p_sep_1) (+ (NTH 1 p_sep_1) lado) (NTH 2 p_sep_1)))
      (setq p_sep_3 (list (NTH 0 p_sep_2) (NTH 1 p_sep_2) (+ (NTH 2 p_sep_2) 0.02)))
      (setq p_sep_4 (list (NTH 0 p_sep_1) (NTH 1 p_sep_1) (+ (NTH 2 p_sep_1) 0.02)))
      (command "3dpoly" p_sep_1 p_sep_2 p_sep_3 p_sep_4 "c")
      (command "revolve" (entlast) "" p_sep_1 p_sep_2 "")
      (command "_color" 2)
      (command "sphere" pun_separador1 radio_sep)
      (command "array" (entlast) "" "r" numbloc1 1 diametro_separador)
      (setq pun_separador2 (list (NTH 0 pun_separador1) (+ (NTH 1 pun_separador1) (/ lado 4)) (NTH 2 pun_separador1)))
      (command "_color" 1)
      (command "sphere" pun_separador2 radio_sep)
      (command "array" (entlast) "" "r" numbloc2 1 diametro_separador)
      (setq pun_separador3 (list (NTH 0 pun_separador2) (+ (NTH 1 pun_separador2) (/ lado 2)) (NTH 2 pun_separador2)))
      (command "_color" 2)
      (command "sphere" pun_separador3 radio_sep)
      (command "array" (entlast) "" "r" numbloc1 1 diametro_separador)
      (setq enti1 (ssget "x" '((8 . "nueva"))))
      (command "change" enti1 "" "p" "la" "0" "")
      (command "-layer" "set" "0" "")
      ;luces
      (command "-layer" "set" "0" "")
      (if (<= lado 16)
	(progn
	  (command "_color" 7)
	  (setq punto_luz (list (+ (NTH 0 p_in) (/ lado 3)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 2 (/ lado 3))))
      (if (>= lado 17)
	(progn
	  (command "_color" 7)
	  (setq punto_luz (list (+ (NTH 0 p_in) (/ lado 4)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 3 (/ lado 4))))

      (command "-layer" "set" "0" "")
      (command "union" "all" "")
      (command "regen")
      (command "purge" "all" "" "n")
      (command "hide")
      
      ))
  (if (= num_tram 2);profundidad= 4 mts; tramp = 5 mts
    (progn
      ;creacion del hueco de la pileta
      (setq prof 4)
      (command "_color" 4)
      (command "box" p_in "l" lado lado prof)
      (setq hueco_pileta (entlast))
      (setq p_in_ext (list (- (NTH 0 p_in) 0.15) (- (NTH 1 p_in) 0.15) (- (NTH 2 p_in) 0.15)))
      (command "_color" 8)
      (command "box" p_in_ext "l" (+ lado 0.30) (+ lado 0.30) (+ prof 0.15))
      (command "subtract" (entlast) "" hueco_pileta "")

      ;borde de la pileta
      (command "_color" 8)
      (setq p_aux (list (NTH 0 p_in_ext) (NTH 1 p_in_ext) (+ (NTH 2 p_in_ext) (+ prof 0.15))))
      (command "box" p_aux "l" (+ (+ lado 0.30) (- ancho_borde 0.15)) (* (- ancho_borde 0.15) -1) -0.3)
      (setq borde1 (entlast))
      (setq p_aux1 (list (+ (NTH 0 p_aux) (+ lado 0.30)) (NTH 1 p_aux) (NTH 2 p_aux)))
      (command "box" p_aux1 "l" (- ancho_borde 0.15) (+ (- ancho_borde 0.15) (+ lado 0.30)) -0.3)
      (setq borde2 (entlast))
      (setq p_aux2 (list (NTH 0 p_aux1) (+ (NTH 1 p_aux1) (+ lado 0.30)) (NTH 2 p_aux1)))
      (command "box" p_aux2 "l" (* (+ (+ lado 0.30) (- ancho_borde 0.15)) -1) (- ancho_borde 0.15) -0.3)
      (setq borde3 (entlast))
      (setq p_aux3 (list (- (NTH 0 p_aux2) (+ lado 0.30)) (NTH 1 p_aux2) (NTH 2 p_aux2)))
      (command "box" p_aux3 "l" (* (- ancho_borde 0.15) -1) (* (+ (- ancho_borde 0.15) (+ lado 0.30)) -1) -0.3)
      (setq borde4 (entlast))
      (command "union" borde1 borde2 borde3 borde4 "")
      (setq p_p_aux (list (NTH 0 p_aux) (+ (- (NTH 1 p_aux) ancho_borde) 0.15) (NTH 2 p_aux)))
      (command "box" p_p_aux "l" -6 (+ (* ancho_borde 2) lado) -0.3)
      (command "zoom" "e")

      ;suavisado bordes
      (command "zoom" "e")
      (command "_color" 4)
      (setq p_aux4 (list (NTH 0 p_in) (+ (NTH 1 p_in) (/ lado 2)) (NTH 2 p_in)))
      (command "fillet" p_aux4 0.15 "")
      (setq p_aux5 (list (+ (NTH 0 p_in) (/ lado 2)) (NTH 1 p_in) (NTH 2 p_in)))
      (command "fillet" p_aux5 0.15 "")
      (setq p_aux6 (list (+ (NTH 0 p_in) (/ lado 2)) (+ (NTH 1 p_in) lado) (NTH 2 p_in)))
      (command "fillet" p_aux6 0.15 "")
      (setq p_aux7 (list (+ (NTH 0 p_in) lado) (+ (NTH 1 p_in) (/ lado 2)) (NTH 2 p_in)))
      (command "fillet" p_aux7 0.15 "")

      (setq p_aux8 (list (NTH 0 p_in) (NTH 1 p_in) (+ (NTH 2 p_in) 1)))
      (command "fillet" p_aux8 0.15 "")
      (setq p_aux9 (list (NTH 0 p_in) (+ (NTH 1 p_in) lado) (+ (NTH 2 p_in) 1)))
      (command "fillet" p_aux9 0.15 "")
      (setq p_aux10 (list (+ (NTH 0 p_in) lado) (NTH 1 p_in) (+ (NTH 2 p_in) 1)))
      (command "fillet" p_aux10 0.15 "")
      (setq p_aux11 (list (+ (NTH 0 p_in) lado) (+ (NTH 1 p_in) lado) (+ (NTH 2 p_in) 1)))
      (command "fillet" p_aux11 0.15 "")

      ;trampolin
      (command "_color" 8)
      (setq alt 5)
      (if (= resp "si")
	(progn
	  (setq pbox (list (- (NTH 0 p_in) 2.5) (- (+ (NTH 1 p_in) (/ (/ lado 2) 2)) 0.5625) (+ (NTH 2 p_in) prof)))));desde este punto al agua hay 2.25 mts por regla, como ancho del box recto, tomo la mitad de esta distancia
      (if (= resp "no")
	(progn
	  (setq pbox (list (- (NTH 0 p_in) 2.5) (- (+ (NTH 1 p_in) (/ lado 2)) 0.5625) (+ (NTH 2 p_in) prof)))))
      (command "box" pbox "l" 1.125 1.125 (+ alt 1))
      (command "wedge" pbox "l" -2.59 1.125 (+ alt 1))
      (setq p_sop (list (NTH 0 pbox) (+ (NTH 1 pbox) 1.125) (+ (NTH 2 pbox) 2.75)));el ancho maximo de la plataforma es 75 cm
      (command "_color" 7)
      (command "wedge" p_sop "l" 4.3 2.75 -0.50)
      (command "wedge" p_sop "l" -2.59 2.75 -0.50)
      (command "box" p_sop "l" 4.3 2.75 0.25)
      (command "box" p_sop "l" -2.59 2.75 0.25)
      (setq p_escalera1 (list (- (NTH 0 p_sop) 2.4) (+ (NTH 1 p_sop) 2.75) (+ (NTH 2 p_sop) 0.25)))
      (setq p_escalera2 (list (+ (NTH 0 p_escalera1) 0.5) (NTH 1 p_escalera1) (NTH 2 p_escalera1)))
      (command "cylinder" p_escalera1 0.05 -3)
      (command "cylinder" p_escalera2 0.05 -3)
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" 11 1 -0.25)
      (command "ucs" "w")

      ;barandas
      (setq p_baranda1 (list (NTH 0 p_sop) (+ (NTH 1 p_sop) 0.05) (+ (NTH 2 p_sop) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq punmirr1 (list (NTH 0 p_sop) (+ (NTH 1 p_sop) 1.375) (NTH 2 p_sop)))
      (setq punmirr2 (list (- (NTH 0 punmirr1) 2.59) (NTH 1 punmirr1) (NTH 2 punmirr1)))
      (command "mirror" prim_cil (entlast) "" punmirr1 punmirr2 "")
      
      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (+ (NTH 1 p_baranda1) 2.65) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;segundo trampolin
      (setq p_sop1 (list (NTH 0 pbox) (- (NTH 1 pbox) 2.75) (+ (NTH 2 pbox) (- alt 0.25))));el ancho maximo de la plataforma es 75 cm
      (command "wedge" p_sop1 "l" 4.3 2.75 -0.50)
      (command "wedge" p_sop1 "l" -2.59 2.75 -0.50)
      (command "box" p_sop1 "l" 4.3 2.75 0.25)
      (command "box" p_sop1 "l" -2.59 2.75 0.25)
      (setq p_escalera1 (list (- (NTH 0 p_sop1) 2.4) (NTH 1 p_sop1) (+ (NTH 2 p_sop1) 0.25)))
      (setq p_escalera2 (list (+ (NTH 0 p_escalera1) 0.5) (NTH 1 p_escalera1) (NTH 2 p_escalera1)))
      (command "cylinder" p_escalera1 0.05 (* alt -1))
      (command "cylinder" p_escalera2 0.05 (* alt -1))
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" (- (/ (* alt 100) 25) 1) 1 -0.25)
      (command "ucs" "w")

      ;barandas
      (setq p_baranda1 (list (NTH 0 p_sop1) (+ (NTH 1 p_sop1) 0.05) (+ (NTH 2 p_sop1) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq punmirr1 (list (NTH 0 p_sop1) (+ (NTH 1 p_sop1) 1.375) (NTH 2 p_sop1)))
      (setq punmirr2 (list (- (NTH 0 punmirr1) 2.59) (NTH 1 punmirr1) (NTH 2 punmirr1)))
      (command "mirror" prim_cil (entlast) "" punmirr1 punmirr2 "")
      
      (setq p_sep_1 (list (NTH 0 p_baranda1) (+ (NTH 1 p_baranda1) 2.65) (+ (NTH 2 p_baranda1) 0.95)))
      (setq p_sep_2 (list (NTH 0 p_baranda2) (+ (NTH 1 p_baranda2) 2.65) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (NTH 1 p_baranda1) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;tramp_extras
      (if (= resp "si")
	(progn
	  (setq pbox (list (- (NTH 0 p_in) 2.5) (- (+ (NTH 1 p_in) (- lado (/ (/ lado 2) 2))) 2.5) (+ (NTH 2 p_in) prof)))
	  (command "box" pbox "l" 2.5 6 0.75)
	  (setq pboxaux (list (NTH 0 pbox) (+ (NTH 1 pbox) 0.1) (NTH 2 pbox)))
	  (command "layer" "m" "tramp_chico" "" "")
	  (command "box" pboxaux "l" -0.25 0.5 0.5)
	  (setq pbox2 (list (- (NTH 0 pboxaux) 0.25) (NTH 1 pboxaux) (NTH 2 pboxaux)))
	  (command "box" pbox2 "l" -0.25 0.5 0.25)
	  (setq pbar1 (list (+ (NTH 0 pbox) 0.05) (+ (NTH 1 pbox) 0.05) (+ (NTH 2 pbox) 0.75)))
	  (setq pbar2 (list (+ (NTH 0 pbar1) 2.4) (NTH 1 pbar1) (NTH 2 pbar1)))
	  (command "cylinder" pbar1 0.05 1)
	  (command "cylinder" pbar2 0.05 1)
	  (setq p1 (list (NTH 0 pbar1) (NTH 1 pbar1) (+ (NTH 2 pbar1) 0.95)))
	  (setq p2 (list (NTH 0 pbar2) (NTH 1 pbar2) (+ (NTH 2 pbar2) 0.95)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_cil1 (list (+ (NTH 0 pbox) 1.3) (+ (NTH 1 pbox) 1.2) (+ (NTH 2 pbox) 0.75)))
	  (setq p_cil2 (list (NTH 0 p_cil1) (+ (NTH 1 p_cil1) 0.6) (NTH 2 p_cil1)))
	  (command "cylinder" p_cil1 0.05 0.15)
	  (command "cylinder" p_cil2 0.05 0.15)
	  (setq p_circ1 (list (NTH 0 p_cil1) (NTH 1 p_cil1) (+ (NTH 2 p_cil1) 0.15)))
	  (setq p_circ2 (list (NTH 0 p_cil2) (NTH 1 p_cil2) (+ (NTH 2 p_cil2) 0.15)))
	  (command "circle" p_circ1 0.05)
	  (setq cir1 (entlast))
	  (command "circle" p_circ2 0.05)
	  (setq cir2 (entlast))
	  (setq p_rev1 (list (NTH 0 p_circ1) (+ (NTH 1 p_circ1) 0.05) (NTH 2 p_circ1)))
	  (setq p_rev2 (list (- (NTH 0 p_rev1) 0.1) (NTH 1 p_rev1) (NTH 2 p_rev1)))
	  (setq p_rev11 (list (NTH 0 p_circ2) (- (NTH 1 p_circ2) 0.05) (NTH 2 p_circ2)))
	  (setq p_rev22 (list (- (NTH 0 p_rev11) 0.1) (NTH 1 p_rev11) (NTH 2 p_rev11)))
	  (command "revolve" cir1 "" p_rev1 p_rev2 90)
	  (command "revolve" cir2 "" p_rev11 p_rev22 -90)
	  (setq p1 (list (NTH 0 p_cil1) (+ (NTH 1 p_cil1) 0.05) (+ (NTH 2 p_cil1) 0.2)))
	  (setq p2 (list (NTH 0 p1) (+ (NTH 1 p1) 0.5) (NTH 2 p1)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_tramp (list (NTH 0 p1) (NTH 1 p1) (+ (NTH 2 p1) 0.05)))
	  (command "box" p_tramp "l" 3 0.5 0.05)
	  (setq p_boxtramp (list (+ (NTH 0 p_tramp) 0.6) (+ (NTH 1 p_tramp) 0.05) (NTH 2 p_tramp)))
	  (command "box" p_boxtramp "l" 0.4 0.4 -0.25)
	  (setq pmirr1 (list (+ (NTH 0 pbox) 2.5) (+ (NTH 1 pbox) 3) (+ (NTH 2 pbox) 0.75)))
	  (setq pmirr2 (list (- (NTH 0 pmirr1) 2.5) (NTH 1 pmirr1) (NTH 2 pmirr1)))
	  (setq enti (ssget "x" '((8 . "tramp_chico"))))
	  (command "mirror" enti "" pmirr1 pmirr2 "")
	  (setq enti1 (ssget "x" '((8 . "tramp_chico"))))
	  (command "change" enti1 "" "p" "la" "0" "")
	  (command "-layer" "set" "0" "")
	  )
	)

      ;ESCALERAS
      (command "-layer" "n" "escaleras" "set" "escaleras" "")
      (command "ucs" "w")
      ;definir punto de inicio escalera
      (setq p0 (list (+ (nth 0 p_in) 0.3) (+ (nth 1 p_in) (+ lado 0.3)) (+ (nth 2 p_in) prof)));punto inicio de la escalera
      ;cilindro 1
      (command "cylinder" p0 0.02 0.45)
      (setq cilindro1 (entlast))
      ;cilindro curvo 1
      (command "zoom" "e")
      (setq p1 (list (nth 0 p0) (nth 1 p0) (+(nth 2 p0)0.45) ))
      (command "circle" p1 0.02 "")
      (setq circulo1 (entlast))
      (setq p1Eje (list (nth 0 p1) (- (nth 1 p1) 0.3) (nth 2 p1) ))
      (setq p2Eje (list (- (nth 0 p1) 0.3) (- (nth 1 p1) 0.3) (nth 2 p1)))
      (command "revolve" circulo1 "" p1Eje p2Eje -180 "")
      (setq cilindroCurvo (entlast))
      ;cilindro 2
      (setq p2 (list (nth 0 p1) (-(nth 1 p1)0.60) (nth 2 p1)))
      (command "cylinder" p2 0.02 -1.45)
      (setq cilindro2 (entlast))
      ;cilindro curvo 2
      (setq p3 (list (nth 0 p2) (nth 1 p2) (-(nth 2 p2) 1.45)))
      (command "circle" p3 0.02 "")
      (setq circulo2 (entlast))
      (setq p1Eje2 (list (nth 0 p3) (+ (nth 1 p3) 0.3) (nth 2 p3)))
      (setq p2Eje2 (list (+ (nth 0 p3) 0.3) (+ (nth 1 p3) 0.3) (nth 2 p3)))
      (command "revolve" circulo2 "" p1Eje2 p2Eje2 90 "")
      (setq cilindroCurvo2 (entlast))
      (command "union"  cilindro1 cilindroCurvo cilindro2 cilindroCurvo2 "")
      (setq canio1 (entlast))
      ;caño dos
      (setq p0Canio2 (list (+ (nth 0 p0) 0.5) (nth 1 p0)(nth 2 p0)))
      (command "copy" canio1 "" p0  p0Canio2)
      ;escalones
      (setq p1Escalon (list (nth 0 p2) (-(nth 1 p2) 0.075) (-(nth 2 p2)0.65)));
      (command "box" p1Escalon "l" 0.5 0.15 -0.03)
      (setq escalon (entlast))
      (command "ucs" "x" 90)
      (command "array" escalon "" "r" 4 1 -0.25)
      (command "ucs" "w")
      (command "-layer" "set" "escaleras" "")
      (setq escaleraTodo (ssget "x" '((8 . "escaleras"))))
      (command "union" escaleraTodo "" )
      (setq escComp (entlast));escalera
      ;escalera 2
      (command "zoom" "e")
      (setq mir1 (list (+ (NTH 0 p_in) (/ lado 2)) (NTH 1 p_in) (NTH 2 p_in)))
      (setq mir2 (list (NTH 0 mir1) (+ (NTH 1 mir1) lado) (NTH 2 mir1)))
      (command "mirror" escComp "" mir1 mir2 "")
      (setq escComp2 (entlast))
      ;miror
      (setq mi1l (list (+ (NTH 0 p_in) lado) (+ (NTH 1 p_in) (/ lado 2)) (NTH 2 p_in)))
      (setq mi2l (list (- (NTH 0 mi1l) lado) (NTH 1 mi1l) (NTH 2 mi1l)))
      (command "mirror" escComp escComp2 "" mi1l mi2l "")
      (setq enti1 (ssget "x" '((8 . "escaleras"))))
      (command "change" enti1 "" "p" "la" "0" "")
      (command "-layer" "set" "0" "")

      ;seeparador
      (command "layer" "m" "nueva" "" "")
      (setq radio_sep (/ diametro_separador 2))
      (setq numbloc1 (fix (/ (/ lado 4) diametro_separador))
	    numbloc2 (fix (/ (/ lado 2) diametro_separador)))
      (setq pun_separador1 (list (+ (NTH 0 p_in) (/ (* lado 80) 100)) (+ (NTH 1 p_in) radio_sep) (+ (NTH 2 p_in) (- prof 0.1))))
      (setq p_sep_1 (list (NTH 0 pun_separador1) (- (NTH 1 pun_separador1) radio_sep) (- (NTH 2 pun_separador1) 0.01)))
      (setq p_sep_2 (list (NTH 0 p_sep_1) (+ (NTH 1 p_sep_1) lado) (NTH 2 p_sep_1)))
      (setq p_sep_3 (list (NTH 0 p_sep_2) (NTH 1 p_sep_2) (+ (NTH 2 p_sep_2) 0.02)))
      (setq p_sep_4 (list (NTH 0 p_sep_1) (NTH 1 p_sep_1) (+ (NTH 2 p_sep_1) 0.02)))
      (command "3dpoly" p_sep_1 p_sep_2 p_sep_3 p_sep_4 "c")
      (command "revolve" (entlast) "" p_sep_1 p_sep_2 "")
      (command "_color" 2)
      (command "sphere" pun_separador1 radio_sep)
      (command "array" (entlast) "" "r" numbloc1 1 diametro_separador)
      (setq pun_separador2 (list (NTH 0 pun_separador1) (+ (NTH 1 pun_separador1) (/ lado 4)) (NTH 2 pun_separador1)))
      (command "_color" 1)
      (command "sphere" pun_separador2 radio_sep)
      (command "array" (entlast) "" "r" numbloc2 1 diametro_separador)
      (setq pun_separador3 (list (NTH 0 pun_separador2) (+ (NTH 1 pun_separador2) (/ lado 2)) (NTH 2 pun_separador2)))
      (command "_color" 2)
      (command "sphere" pun_separador3 radio_sep)
      (command "array" (entlast) "" "r" numbloc1 1 diametro_separador)
      (setq enti1 (ssget "x" '((8 . "nueva"))))
      (command "change" enti1 "" "p" "la" "0" "")
      (command "-layer" "set" "0" "")
      ;luces
      (command "-layer" "set" "0" "")
      (if (<= lado 16)
	(progn
	  (command "_color" 7)
	  (setq punto_luz (list (+ (NTH 0 p_in) (/ lado 3)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 2 (/ lado 3))))
      (if (>= lado 17)
	(progn
	  (command "_color" 7)
	  (setq punto_luz (list (+ (NTH 0 p_in) (/ lado 4)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 3 (/ lado 4))))
      (command "-layer" "set" "0" "")
      (command "union" "all" "")
      (command "regen")
      (command "purge" "all" "" "n")
      (command "hide")
      ))

  (if (= num_tram 3);profundidad= 4.5 mts; tramp = 7 mts
    (progn
      ;creacion del hueco de la pileta
      (setq prof 4.5)
      (command "_color" 4)
      (command "box" p_in "l" lado lado prof)
      (setq hueco_pileta (entlast))
      (setq p_in_ext (list (- (NTH 0 p_in) 0.15) (- (NTH 1 p_in) 0.15) (- (NTH 2 p_in) 0.15)))
      (command "_color" 8)
      (command "box" p_in_ext "l" (+ lado 0.30) (+ lado 0.30) (+ prof 0.15))
      (command "subtract" (entlast) "" hueco_pileta "")

      ;borde de la pileta
      (command "_color" 8)
      (setq p_aux (list (NTH 0 p_in_ext) (NTH 1 p_in_ext) (+ (NTH 2 p_in_ext) (+ prof 0.15))))
      (command "box" p_aux "l" (+ (+ lado 0.30) (- ancho_borde 0.15)) (* (- ancho_borde 0.15) -1) -0.3)
      (setq borde1 (entlast))
      (setq p_aux1 (list (+ (NTH 0 p_aux) (+ lado 0.30)) (NTH 1 p_aux) (NTH 2 p_aux)))
      (command "box" p_aux1 "l" (- ancho_borde 0.15) (+ (- ancho_borde 0.15) (+ lado 0.30)) -0.3)
      (setq borde2 (entlast))
      (setq p_aux2 (list (NTH 0 p_aux1) (+ (NTH 1 p_aux1) (+ lado 0.30)) (NTH 2 p_aux1)))
      (command "box" p_aux2 "l" (* (+ (+ lado 0.30) (- ancho_borde 0.15)) -1) (- ancho_borde 0.15) -0.3)
      (setq borde3 (entlast))
      (setq p_aux3 (list (- (NTH 0 p_aux2) (+ lado 0.30)) (NTH 1 p_aux2) (NTH 2 p_aux2)))
      (command "box" p_aux3 "l" (* (- ancho_borde 0.15) -1) (* (+ (- ancho_borde 0.15) (+ lado 0.30)) -1) -0.3)
      (setq borde4 (entlast))
      (command "union" borde1 borde2 borde3 borde4 "")
      (setq p_p_aux (list (NTH 0 p_aux) (+ (- (NTH 1 p_aux) ancho_borde) 0.15) (NTH 2 p_aux)))
      (command "box" p_p_aux "l" -6 (+ (* ancho_borde 2) lado) -0.3)
      (command "zoom" "e")

      ;suavisado bordes
      (command "zoom" "e")
      (command "_color" 4)
      (setq p_aux4 (list (NTH 0 p_in) (+ (NTH 1 p_in) (/ lado 2)) (NTH 2 p_in)))
      (command "fillet" p_aux4 0.15 "")
      (setq p_aux5 (list (+ (NTH 0 p_in) (/ lado 2)) (NTH 1 p_in) (NTH 2 p_in)))
      (command "fillet" p_aux5 0.15 "")
      (setq p_aux6 (list (+ (NTH 0 p_in) (/ lado 2)) (+ (NTH 1 p_in) lado) (NTH 2 p_in)))
      (command "fillet" p_aux6 0.15 "")
      (setq p_aux7 (list (+ (NTH 0 p_in) lado) (+ (NTH 1 p_in) (/ lado 2)) (NTH 2 p_in)))
      (command "fillet" p_aux7 0.15 "")

      (setq p_aux8 (list (NTH 0 p_in) (NTH 1 p_in) (+ (NTH 2 p_in) 1)))
      (command "fillet" p_aux8 0.15 "")
      (setq p_aux9 (list (NTH 0 p_in) (+ (NTH 1 p_in) lado) (+ (NTH 2 p_in) 1)))
      (command "fillet" p_aux9 0.15 "")
      (setq p_aux10 (list (+ (NTH 0 p_in) lado) (NTH 1 p_in) (+ (NTH 2 p_in) 1)))
      (command "fillet" p_aux10 0.15 "")
      (setq p_aux11 (list (+ (NTH 0 p_in) lado) (+ (NTH 1 p_in) lado) (+ (NTH 2 p_in) 1)))
      (command "fillet" p_aux11 0.15 "")

      ;luces
      (if (<= lado 16)
	(progn
	  (command "_color" 7)
	  (setq punto_luz (list (+ (NTH 0 p_in) (/ lado 3)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 2 (/ lado 3))))
      (if (>= lado 17)
	(progn
	  (command "_color" 7)
	  (setq punto_luz (list (+ (NTH 0 p_in) (/ lado 4)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 3 (/ lado 4))))

      ;trampolin
      (command "_color" 8)
      (setq alt 7)
      (if (= resp "si")
	(progn
	  (setq pbox (list (- (NTH 0 p_in) 2.5) (- (+ (NTH 1 p_in) (/ (/ lado 2) 2)) 0.5625) (+ (NTH 2 p_in) prof)))));desde este punto al agua hay 2.25 mts por regla, como ancho del box recto, tomo la mitad de esta distancia
      (if (= resp "no")
	(progn
	  (setq pbox (list (- (NTH 0 p_in) 2.5) (- (+ (NTH 1 p_in) (/ lado 2)) 0.5625) (+ (NTH 2 p_in) prof)))))
      (command "box" pbox "l" 1.125 1.125 (+ alt 1))
      (command "wedge" pbox "l" -2.59 1.125 (+ alt 1))
      (setq p_sop (list (NTH 0 pbox) (+ (NTH 1 pbox) 1.125) (+ (NTH 2 pbox) 2.75)));el ancho maximo de la plataforma es 75 cm
      (command "_color" 7)
      (command "wedge" p_sop "l" 4.3 2.75 -0.50)
      (command "wedge" p_sop "l" -2.59 2.75 -0.50)
      (command "box" p_sop "l" 4.3 2.75 0.25)
      (command "box" p_sop "l" -2.59 2.75 0.25)
      (setq p_escalera1 (list (- (NTH 0 p_sop) 2.4) (+ (NTH 1 p_sop) 2.75) (+ (NTH 2 p_sop) 0.25)))
      (setq p_escalera2 (list (+ (NTH 0 p_escalera1) 0.5) (NTH 1 p_escalera1) (NTH 2 p_escalera1)))
      (command "cylinder" p_escalera1 0.05 -3)
      (command "cylinder" p_escalera2 0.05 -3)
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" 11 1 -0.25)
      (command "ucs" "w")

      ;barandas
      (setq p_baranda1 (list (NTH 0 p_sop) (+ (NTH 1 p_sop) 0.05) (+ (NTH 2 p_sop) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq punmirr1 (list (NTH 0 p_sop) (+ (NTH 1 p_sop) 1.375) (NTH 2 p_sop)))
      (setq punmirr2 (list (- (NTH 0 punmirr1) 2.59) (NTH 1 punmirr1) (NTH 2 punmirr1)))
      (command "mirror" prim_cil (entlast) "" punmirr1 punmirr2 "")
      
      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (+ (NTH 1 p_baranda1) 2.65) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;segundo trampolin

      (setq p_sop1 (list (NTH 0 pbox) (- (NTH 1 pbox) 2.75) (+ (NTH 2 pbox) 4.75)));el ancho maximo de la plataforma es 75 cm
      (command "wedge" p_sop1 "l" 4.3 2.75 -0.50)
      (command "wedge" p_sop1 "l" -2.59 2.75 -0.50)
      (command "box" p_sop1 "l" 4.3 2.75 0.25)
      (command "box" p_sop1 "l" -2.59 2.75 0.25)
      (setq p_escalera1 (list (- (NTH 0 p_sop1) 2.4) (NTH 1 p_sop1) (+ (NTH 2 p_sop1) 0.25)))
      (setq p_escalera2 (list (+ (NTH 0 p_escalera1) 0.5) (NTH 1 p_escalera1) (NTH 2 p_escalera1)))
      (command "cylinder" p_escalera1 0.05 -5)
      (command "cylinder" p_escalera2 0.05 -5)
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" 19 1 -0.25)
      (command "ucs" "w")

      ;barandas
      (setq p_baranda1 (list (NTH 0 p_sop1) (+ (NTH 1 p_sop1) 0.05) (+ (NTH 2 p_sop1) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq punmirr1 (list (NTH 0 p_sop1) (+ (NTH 1 p_sop1) 1.375) (NTH 2 p_sop1)))
      (setq punmirr2 (list (- (NTH 0 punmirr1) 2.59) (NTH 1 punmirr1) (NTH 2 punmirr1)))
      (command "mirror" prim_cil (entlast) "" punmirr1 punmirr2 "")
      
      (setq p_sep_1 (list (NTH 0 p_baranda1) (+ (NTH 1 p_baranda1) 2.65) (+ (NTH 2 p_baranda1) 0.95)))
      (setq p_sep_2 (list (NTH 0 p_baranda2) (+ (NTH 1 p_baranda2) 2.65) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (NTH 1 p_baranda1) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;tercer trampolin

      (setq p_sop2 (list (NTH 0 pbox) (+ (NTH 1 pbox) 1.125) (+ (NTH 2 pbox) (- alt 0.25))));el ancho maximo de la plataforma es 75 cm
      (command "wedge" p_sop2 "l" 4.3 2.75 -0.50)
      (command "wedge" p_sop2 "l" -2.59 2.75 -0.50)
      (command "box" p_sop2 "l" 4.3 2.75 0.25)
      (command "box" p_sop2 "l" -2.59 2.75 0.25)
      (setq p_escalera1 (list (- (NTH 0 p_sop2) 2.59) (+ (NTH 1 p_sop2) 1.125) (+ (NTH 2 p_sop2) 0.25)))
      (setq p_escalera2 (list (NTH 0 p_escalera1) (+ (NTH 1 p_escalera1) 0.5) (NTH 2 p_escalera1)))
      (command "cylinder" p_escalera1 0.05 (* alt -1))
      (command "cylinder" p_escalera2 0.05 (* alt -1))
      (setq p_escalon (list (- (NTH 0 p_escalera1) 0.025) (+ (NTH 1 p_escalera1) 0.05) (- (NTH 2 p_escalera1) 0.25)))
      (command "box" p_escalon "l" 0.04 0.4 -0.02)
      (command "ucs" "x" "90")
      (command "array" (entlast) "" "r" (- (/ (* alt 100) 25) 1) 1 -0.25)
      (command "ucs" "w")

      ;barandas
      (command "layer" "m" "nueva2" "" "")
      (setq p_baranda1 (list (NTH 0 p_sop2) (+ (NTH 1 p_sop2) 0.05) (+ (NTH 2 p_sop2) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)

      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (NTH 0 p_baranda2) (+ (NTH 1 p_baranda2) 0.825) (NTH 2 p_baranda2)))
      (command "cylinder" p_cil 0.05 1)
      (setq p_sep_1 (list (NTH 0 p_cil) (NTH 1 p_cil) (+ (NTH 2 p_cil) 0.95)))
      (setq p_sep_2 (list (NTH 0 p_sep_1) (- (NTH 1 p_sep_1) 0.825) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq punmirr1 (list (NTH 0 p_sop2) (+ (NTH 1 p_sop2) 1.375) (NTH 2 p_sop2)))
      (setq punmirr2 (list (- (NTH 0 punmirr1) 2.59) (NTH 1 punmirr1) (NTH 2 punmirr1)))
      (setq enti (ssget "x" '((8 . "nueva2"))))
      (command "mirror" enti "" punmirr1 punmirr2 "")
      (setq enti1 (ssget "x" '((8 . "nueva2"))))
      (command "change" enti1 "" "p" "la" "0" "")
      (command "-layer" "set" "0" "")

      ;tramp_extras
      (if (= resp "si")
	(progn
	  (setq pbox (list (- (NTH 0 p_in) 2.5) (- (+ (NTH 1 p_in) (- lado (/ (/ lado 2) 2))) 2.5) (+ (NTH 2 p_in) prof)))
	  (command "box" pbox "l" 2.5 6 0.75)
	  (setq pboxaux (list (NTH 0 pbox) (+ (NTH 1 pbox) 0.1) (NTH 2 pbox)))
	  (command "layer" "m" "tramp_chico" "" "")
	  (command "box" pboxaux "l" -0.25 0.5 0.5)
	  (setq pbox2 (list (- (NTH 0 pboxaux) 0.25) (NTH 1 pboxaux) (NTH 2 pboxaux)))
	  (command "box" pbox2 "l" -0.25 0.5 0.25)
	  (setq pbar1 (list (+ (NTH 0 pbox) 0.05) (+ (NTH 1 pbox) 0.05) (+ (NTH 2 pbox) 0.75)))
	  (setq pbar2 (list (+ (NTH 0 pbar1) 2.4) (NTH 1 pbar1) (NTH 2 pbar1)))
	  (command "cylinder" pbar1 0.05 1)
	  (command "cylinder" pbar2 0.05 1)
	  (setq p1 (list (NTH 0 pbar1) (NTH 1 pbar1) (+ (NTH 2 pbar1) 0.95)))
	  (setq p2 (list (NTH 0 pbar2) (NTH 1 pbar2) (+ (NTH 2 pbar2) 0.95)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_cil1 (list (+ (NTH 0 pbox) 1.3) (+ (NTH 1 pbox) 1.2) (+ (NTH 2 pbox) 0.75)))
	  (setq p_cil2 (list (NTH 0 p_cil1) (+ (NTH 1 p_cil1) 0.6) (NTH 2 p_cil1)))
	  (command "cylinder" p_cil1 0.05 0.15)
	  (command "cylinder" p_cil2 0.05 0.15)
	  (setq p_circ1 (list (NTH 0 p_cil1) (NTH 1 p_cil1) (+ (NTH 2 p_cil1) 0.15)))
	  (setq p_circ2 (list (NTH 0 p_cil2) (NTH 1 p_cil2) (+ (NTH 2 p_cil2) 0.15)))
	  (command "circle" p_circ1 0.05)
	  (setq cir1 (entlast))
	  (command "circle" p_circ2 0.05)
	  (setq cir2 (entlast))
	  (setq p_rev1 (list (NTH 0 p_circ1) (+ (NTH 1 p_circ1) 0.05) (NTH 2 p_circ1)))
	  (setq p_rev2 (list (- (NTH 0 p_rev1) 0.1) (NTH 1 p_rev1) (NTH 2 p_rev1)))
	  (setq p_rev11 (list (NTH 0 p_circ2) (- (NTH 1 p_circ2) 0.05) (NTH 2 p_circ2)))
	  (setq p_rev22 (list (- (NTH 0 p_rev11) 0.1) (NTH 1 p_rev11) (NTH 2 p_rev11)))
	  (command "revolve" cir1 "" p_rev1 p_rev2 90)
	  (command "revolve" cir2 "" p_rev11 p_rev22 -90)
	  (setq p1 (list (NTH 0 p_cil1) (+ (NTH 1 p_cil1) 0.05) (+ (NTH 2 p_cil1) 0.2)))
	  (setq p2 (list (NTH 0 p1) (+ (NTH 1 p1) 0.5) (NTH 2 p1)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_tramp (list (NTH 0 p1) (NTH 1 p1) (+ (NTH 2 p1) 0.05)))
	  (command "box" p_tramp "l" 3 0.5 0.05)
	  (setq p_boxtramp (list (+ (NTH 0 p_tramp) 0.6) (+ (NTH 1 p_tramp) 0.05) (NTH 2 p_tramp)))
	  (command "box" p_boxtramp "l" 0.4 0.4 -0.25)
	  (setq pmirr1 (list (+ (NTH 0 pbox) 2.5) (+ (NTH 1 pbox) 3) (+ (NTH 2 pbox) 0.75)))
	  (setq pmirr2 (list (- (NTH 0 pmirr1) 2.5) (NTH 1 pmirr1) (NTH 2 pmirr1)))
	  (setq enti (ssget "x" '((8 . "tramp_chico"))))
	  (command "mirror" enti "" pmirr1 pmirr2 "")
	  (setq enti1 (ssget "x" '((8 . "tramp_chico"))))
	  (command "change" enti1 "" "p" "la" "0" "")
	  (command "-layer" "set" "0" "")
	  
	  )
	)

      ;ESCALERAS
      (command "-layer" "n" "escaleras" "set" "escaleras" "")
      (command "ucs" "w")
      ;definir punto de inicio escalera
      (setq p0 (list (+ (nth 0 p_in) 0.3) (+ (nth 1 p_in) (+ lado 0.3)) (+ (nth 2 p_in) prof)));punto inicio de la escalera
      ;cilindro 1
      (command "cylinder" p0 0.02 0.45)
      (setq cilindro1 (entlast))
      ;cilindro curvo 1
      (command "zoom" "e")
      (setq p1 (list (nth 0 p0) (nth 1 p0) (+(nth 2 p0)0.45) ))
      (command "circle" p1 0.02 "")
      (setq circulo1 (entlast))
      (setq p1Eje (list (nth 0 p1) (- (nth 1 p1) 0.3) (nth 2 p1) ))
      (setq p2Eje (list (- (nth 0 p1) 0.3) (- (nth 1 p1) 0.3) (nth 2 p1)))
      (command "revolve" circulo1 "" p1Eje p2Eje -180 "")
      (setq cilindroCurvo (entlast))
      ;cilindro 2
      (setq p2 (list (nth 0 p1) (-(nth 1 p1)0.60) (nth 2 p1)))
      (command "cylinder" p2 0.02 -1.45)
      (setq cilindro2 (entlast))
      ;cilindro curvo 2
      (setq p3 (list (nth 0 p2) (nth 1 p2) (-(nth 2 p2) 1.45)))
      (command "circle" p3 0.02 "")
      (setq circulo2 (entlast))
      (setq p1Eje2 (list (nth 0 p3) (+ (nth 1 p3) 0.3) (nth 2 p3)))
      (setq p2Eje2 (list (+ (nth 0 p3) 0.3) (+ (nth 1 p3) 0.3) (nth 2 p3)))
      (command "revolve" circulo2 "" p1Eje2 p2Eje2 90 "")
      (setq cilindroCurvo2 (entlast))
      (command "union"  cilindro1 cilindroCurvo cilindro2 cilindroCurvo2 "")
      (setq canio1 (entlast))
      ;caño dos
      (setq p0Canio2 (list (+ (nth 0 p0) 0.5) (nth 1 p0)(nth 2 p0)))
      (command "copy" canio1 "" p0  p0Canio2)
      ;escalones
      (setq p1Escalon (list (nth 0 p2) (-(nth 1 p2) 0.075) (-(nth 2 p2)0.65)));
      (command "box" p1Escalon "l" 0.5 0.15 -0.03)
      (setq escalon (entlast))
      (command "ucs" "x" 90)
      (command "array" escalon "" "r" 4 1 -0.25)
      (command "ucs" "w")
      (command "-layer" "set" "escaleras" "")
      (setq escaleraTodo (ssget "x" '((8 . "escaleras"))))
      (command "union" escaleraTodo "" )
      (setq escComp (entlast));escalera
      ;escalera 2
      (command "zoom" "e")
      (setq mir1 (list (+ (NTH 0 p_in) (/ lado 2)) (NTH 1 p_in) (NTH 2 p_in)))
      (setq mir2 (list (NTH 0 mir1) (+ (NTH 1 mir1) lado) (NTH 2 mir1)))
      (command "mirror" escComp "" mir1 mir2 "")
      (setq escComp2 (entlast))
      ;miror
      (setq mi1l (list (+ (NTH 0 p_in) lado) (+ (NTH 1 p_in) (/ lado 2)) (NTH 2 p_in)))
      (setq mi2l (list (- (NTH 0 mi1l) lado) (NTH 1 mi1l) (NTH 2 mi1l)))
      (command "mirror" escComp escComp2 "" mi1l mi2l "")
      (setq enti1 (ssget "x" '((8 . "escaleras"))))
      (command "change" enti1 "" "p" "la" "0" "")
      (command "-layer" "set" "0" "")
      
      ;seeparador
      (command "layer" "m" "nueva" "" "")
      (setq radio_sep (/ diametro_separador 2))
      (setq numbloc1 (fix (/ (/ lado 4) diametro_separador))
	    numbloc2 (fix (/ (/ lado 2) diametro_separador)))
      (setq pun_separador1 (list (+ (NTH 0 p_in) (/ (* lado 80) 100)) (+ (NTH 1 p_in) radio_sep) (+ (NTH 2 p_in) (- prof 0.1))))
      (setq p_sep_1 (list (NTH 0 pun_separador1) (- (NTH 1 pun_separador1) radio_sep) (- (NTH 2 pun_separador1) 0.01)))
      (setq p_sep_2 (list (NTH 0 p_sep_1) (+ (NTH 1 p_sep_1) lado) (NTH 2 p_sep_1)))
      (setq p_sep_3 (list (NTH 0 p_sep_2) (NTH 1 p_sep_2) (+ (NTH 2 p_sep_2) 0.02)))
      (setq p_sep_4 (list (NTH 0 p_sep_1) (NTH 1 p_sep_1) (+ (NTH 2 p_sep_1) 0.02)))
      (command "3dpoly" p_sep_1 p_sep_2 p_sep_3 p_sep_4 "c")
      (command "revolve" (entlast) "" p_sep_1 p_sep_2 "")
      (command "_color" 2)
      (command "sphere" pun_separador1 radio_sep)
      (command "array" (entlast) "" "r" numbloc1 1 diametro_separador)
      (setq pun_separador2 (list (NTH 0 pun_separador1) (+ (NTH 1 pun_separador1) (/ lado 4)) (NTH 2 pun_separador1)))
      (command "_color" 1)
      (command "sphere" pun_separador2 radio_sep)
      (command "array" (entlast) "" "r" numbloc2 1 diametro_separador)
      (setq pun_separador3 (list (NTH 0 pun_separador2) (+ (NTH 1 pun_separador2) (/ lado 2)) (NTH 2 pun_separador2)))
      (command "_color" 2)
      (command "sphere" pun_separador3 radio_sep)
      (command "array" (entlast) "" "r" numbloc1 1 diametro_separador)
      (setq enti1 (ssget "x" '((8 . "nueva"))))
      (command "change" enti1 "" "p" "la" "0" "")
      (command "-layer" "set" "0" "")
      ;luces
      (command "-layer" "set" "0" "")
      (if (<= lado 16)
	(progn
	  (command "_color" 7)
	  (setq punto_luz (list (+ (NTH 0 p_in) (/ lado 3)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 2 (/ lado 3))))
      (if (>= lado 17)
	(progn
	  (command "_color" 7)
	  (setq punto_luz (list (+ (NTH 0 p_in) (/ lado 4)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 3 (/ lado 4))))
      (command "-layer" "set" "0" "")
      (command "union" "all" "")
      (command "regen")
      (command "purge" "all" "" "n")
      (command "hide")
      ))
  
  (if (= num_tram 4);profundidad= 5 mts; tramp = 10 mts
    (progn
      ;creacion del hueco de la pileta
      (setq prof 5)
      (command "_color" 4)
      (command "box" p_in "l" lado lado prof)
      (setq hueco_pileta (entlast))
      (setq p_in_ext (list (- (NTH 0 p_in) 0.15) (- (NTH 1 p_in) 0.15) (- (NTH 2 p_in) 0.15)))
      (command "_color" 8)
      (command "box" p_in_ext "l" (+ lado 0.30) (+ lado 0.30) (+ prof 0.15))
      (command "subtract" (entlast) "" hueco_pileta "")

      ;borde de la pileta
      (command "_color" 8)
      (setq p_aux (list (NTH 0 p_in_ext) (NTH 1 p_in_ext) (+ (NTH 2 p_in_ext) (+ prof 0.15))))
      (command "box" p_aux "l" (+ (+ lado 0.30) (- ancho_borde 0.15)) (* (- ancho_borde 0.15) -1) -0.3)
      (setq borde1 (entlast))
      (setq p_aux1 (list (+ (NTH 0 p_aux) (+ lado 0.30)) (NTH 1 p_aux) (NTH 2 p_aux)))
      (command "box" p_aux1 "l" (- ancho_borde 0.15) (+ (- ancho_borde 0.15) (+ lado 0.30)) -0.3)
      (setq borde2 (entlast))
      (setq p_aux2 (list (NTH 0 p_aux1) (+ (NTH 1 p_aux1) (+ lado 0.30)) (NTH 2 p_aux1)))
      (command "box" p_aux2 "l" (* (+ (+ lado 0.30) (- ancho_borde 0.15)) -1) (- ancho_borde 0.15) -0.3)
      (setq borde3 (entlast))
      (setq p_aux3 (list (- (NTH 0 p_aux2) (+ lado 0.30)) (NTH 1 p_aux2) (NTH 2 p_aux2)))
      (command "box" p_aux3 "l" (* (- ancho_borde 0.15) -1) (* (+ (- ancho_borde 0.15) (+ lado 0.30)) -1) -0.3)
      (setq borde4 (entlast))
      (command "union" borde1 borde2 borde3 borde4 "")
      (setq p_p_aux (list (NTH 0 p_aux) (+ (- (NTH 1 p_aux) ancho_borde) 0.15) (NTH 2 p_aux)))
      (command "box" p_p_aux "l" -6 (+ (* ancho_borde 2) lado) -0.3)
      (command "zoom" "e")

      ;suavisado bordes
      (command "zoom" "e")
      (command "_color" 4)
      (setq p_aux4 (list (NTH 0 p_in) (+ (NTH 1 p_in) (/ lado 2)) (NTH 2 p_in)))
      (command "fillet" p_aux4 0.15 "")
      (setq p_aux5 (list (+ (NTH 0 p_in) (/ lado 2)) (NTH 1 p_in) (NTH 2 p_in)))
      (command "fillet" p_aux5 0.15 "")
      (setq p_aux6 (list (+ (NTH 0 p_in) (/ lado 2)) (+ (NTH 1 p_in) lado) (NTH 2 p_in)))
      (command "fillet" p_aux6 0.15 "")
      (setq p_aux7 (list (+ (NTH 0 p_in) lado) (+ (NTH 1 p_in) (/ lado 2)) (NTH 2 p_in)))
      (command "fillet" p_aux7 0.15 "")

      (setq p_aux8 (list (NTH 0 p_in) (NTH 1 p_in) (+ (NTH 2 p_in) 1)))
      (command "fillet" p_aux8 0.15 "")
      (setq p_aux9 (list (NTH 0 p_in) (+ (NTH 1 p_in) lado) (+ (NTH 2 p_in) 1)))
      (command "fillet" p_aux9 0.15 "")
      (setq p_aux10 (list (+ (NTH 0 p_in) lado) (NTH 1 p_in) (+ (NTH 2 p_in) 1)))
      (command "fillet" p_aux10 0.15 "")
      (setq p_aux11 (list (+ (NTH 0 p_in) lado) (+ (NTH 1 p_in) lado) (+ (NTH 2 p_in) 1)))
      (command "fillet" p_aux11 0.15 "")

      ;luces
      (if (<= lado 16)
	(progn
	  (command "_color" 7)
	  (setq punto_luz (list (+ (NTH 0 p_in) (/ lado 3)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 2 (/ lado 3))))
      (if (>= lado 17)
	(progn
	  (command "_color" 7)
	  (setq punto_luz (list (+ (NTH 0 p_in) (/ lado 4)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 3 (/ lado 4))))

      ;trampolin
      (command "_color" 8)
      (setq alt 10)
      (if (= resp "si")
	(progn
	  (setq pbox (list (- (NTH 0 p_in) 2.5) (- (+ (NTH 1 p_in) (/ (/ lado 2) 2)) 0.5625) (+ (NTH 2 p_in) prof)))));desde este punto al agua hay 2.25 mts por regla, como ancho del box recto, tomo la mitad de esta distancia
      (if (= resp "no")
	(progn
	  (setq pbox (list (- (NTH 0 p_in) 2.5) (- (+ (NTH 1 p_in) (/ lado 2)) 0.5625) (+ (NTH 2 p_in) prof)))))
      (command "box" pbox "l" 1.125 1.125 (+ alt 1))
      (command "wedge" pbox "l" -2.59 1.125 (+ alt 1))
      (setq p_sop (list (NTH 0 pbox) (+ (NTH 1 pbox) 1.125) (+ (NTH 2 pbox) 2.75)));el ancho maximo de la plataforma es 75 cm
      (command "_color" 7)
      (command "wedge" p_sop "l" 4.3 2.75 -0.50)
      (command "wedge" p_sop "l" -2.59 2.75 -0.50)
      (command "box" p_sop "l" 4.3 2.75 0.25)
      (command "box" p_sop "l" -2.59 2.75 0.25)
      (setq p_escalera1 (list (- (NTH 0 p_sop) 2.4) (+ (NTH 1 p_sop) 2.75) (+ (NTH 2 p_sop) 0.25)))
      (setq p_escalera2 (list (+ (NTH 0 p_escalera1) 0.5) (NTH 1 p_escalera1) (NTH 2 p_escalera1)))
      (command "cylinder" p_escalera1 0.05 -3)
      (command "cylinder" p_escalera2 0.05 -3)
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" 11 1 -0.25)
      (command "ucs" "w")

      ;barandas
      (setq p_baranda1 (list (NTH 0 p_sop) (+ (NTH 1 p_sop) 0.05) (+ (NTH 2 p_sop) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq punmirr1 (list (NTH 0 p_sop) (+ (NTH 1 p_sop) 1.375) (NTH 2 p_sop)))
      (setq punmirr2 (list (- (NTH 0 punmirr1) 2.59) (NTH 1 punmirr1) (NTH 2 punmirr1)))
      (command "mirror" prim_cil (entlast) "" punmirr1 punmirr2 "")
      
      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (+ (NTH 1 p_baranda1) 2.65) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;segundo trampolin

      (setq p_sop1 (list (NTH 0 pbox) (- (NTH 1 pbox) 2.75) (+ (NTH 2 pbox) 4.75)));el ancho maximo de la plataforma es 75 cm
      (command "wedge" p_sop1 "l" 4.3 2.75 -0.50)
      (command "wedge" p_sop1 "l" -2.59 2.75 -0.50)
      (command "box" p_sop1 "l" 4.3 2.75 0.25)
      (command "box" p_sop1 "l" -2.59 2.75 0.25)
      (setq p_escalera1 (list (- (NTH 0 p_sop1) 2.4) (NTH 1 p_sop1) (+ (NTH 2 p_sop1) 0.25)))
      (setq p_escalera2 (list (+ (NTH 0 p_escalera1) 0.5) (NTH 1 p_escalera1) (NTH 2 p_escalera1)))
      (command "cylinder" p_escalera1 0.05 -5)
      (command "cylinder" p_escalera2 0.05 -5)
      (setq p_escalon (list (+ (NTH 0 p_escalera1) 0.05) (- (NTH 1 p_escalera1) 0.025) (- (NTH 2 p_escalera1) 0.25)))
      (command "box" p_escalon "l" 0.4 0.04 -0.02)
      (command "ucs" "x" "90")
      (command "array" (entlast) "" "r" 19 1 -0.25)
      (command "ucs" "w")

      ;barandas
      (setq p_baranda1 (list (NTH 0 p_sop1) (+ (NTH 1 p_sop1) 0.05) (+ (NTH 2 p_sop1) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)
      (setq punmirr1 (list (NTH 0 p_sop1) (+ (NTH 1 p_sop1) 1.375) (NTH 2 p_sop1)))
      (setq punmirr2 (list (- (NTH 0 punmirr1) 2.59) (NTH 1 punmirr1) (NTH 2 punmirr1)))
      (command "mirror" prim_cil (entlast) "" punmirr1 punmirr2 "")
      
      (setq p_sep_1 (list (NTH 0 p_baranda1) (+ (NTH 1 p_baranda1) 2.65) (+ (NTH 2 p_baranda1) 0.95)))
      (setq p_sep_2 (list (NTH 0 p_baranda2) (+ (NTH 1 p_baranda2) 2.65) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq p_sep_1 (list (NTH 0 p_baranda2) (NTH 1 p_baranda2) (+ (NTH 2 p_baranda2) 0.95)))
      (setq p_sep_2 (list (NTH 0 p_sep_1) (+ (NTH 1 p_sep_1) 2.65) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (- (NTH 0 p_baranda1) 1.76) (NTH 1 p_baranda1) (NTH 2 p_baranda1)))
      (command "cylinder" p_cil 0.05 1)
      (setq p_sep_1 (list (NTH 0 p_cil) (NTH 1 p_cil) (+ (NTH 2 p_cil) 0.95)))
      (setq p_sep_2 (list (+ (NTH 0 p_sep_1) 1.76) (NTH 1 p_sep_1) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      ;tercer trampolin

      (setq p_sop2 (list (NTH 0 pbox) (+ (NTH 1 pbox) 1.125) (+ (NTH 2 pbox) 6.75)));el ancho maximo de la plataforma es 75 cm
      (command "wedge" p_sop2 "l" 4.3 2.75 -0.50)
      (command "wedge" p_sop2 "l" -2.59 2.75 -0.50)
      (command "box" p_sop2 "l" 4.3 2.75 0.25)
      (command "box" p_sop2 "l" -2.59 2.75 0.25)
      (setq p_escalera1 (list (- (NTH 0 p_sop2) 2.59) (+ (NTH 1 p_sop2) 1.125) (+ (NTH 2 p_sop2) 0.25)))
      (setq p_escalera2 (list (NTH 0 p_escalera1) (+ (NTH 1 p_escalera1) 0.5) (NTH 2 p_escalera1)))
      (command "cylinder" p_escalera1 0.05 -7)
      (command "cylinder" p_escalera2 0.05 -7)
      (setq p_escalon (list (- (NTH 0 p_escalera1) 0.025) (+ (NTH 1 p_escalera1) 0.05) (- (NTH 2 p_escalera1) 0.25)))
      (command "box" p_escalon "l" 0.04 0.4 -0.02)
      (command "ucs" "x" "90")
      (command "array" (entlast) "" "r" 27 1 -0.25)
      (command "ucs" "w")

      ;barandas
      (command "layer" "m" "nueva2" "" "")
      (setq p_baranda1 (list (NTH 0 p_sop2) (+ (NTH 1 p_sop2) 0.05) (+ (NTH 2 p_sop2) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)

      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (NTH 0 p_baranda2) (+ (NTH 1 p_baranda2) 0.825) (NTH 2 p_baranda2)))
      (command "cylinder" p_cil 0.05 1)
      (setq p_sep_1 (list (NTH 0 p_cil) (NTH 1 p_cil) (+ (NTH 2 p_cil) 0.95)))
      (setq p_sep_2 (list (NTH 0 p_sep_1) (- (NTH 1 p_sep_1) 0.825) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq punmirr1 (list (NTH 0 p_sop2) (+ (NTH 1 p_sop2) 1.375) (NTH 2 p_sop2)))
      (setq punmirr2 (list (- (NTH 0 punmirr1) 2.59) (NTH 1 punmirr1) (NTH 2 punmirr1)))
      (setq enti (ssget "x" '((8 . "nueva2"))))
      (command "mirror" enti "" punmirr1 punmirr2 "")
      (setq enti1 (ssget "x" '((8 . "nueva2"))))
      (command "change" enti1 "" "p" "la" "0" "")
      (command "-layer" "set" "0" "")

      ;cuarto trampolin

      (setq p_sop3 (list (NTH 0 pbox) (- (NTH 1 pbox) 2.75) (+ (NTH 2 pbox) (- alt 0.25))));el ancho maximo de la plataforma es 75 cm
      (command "wedge" p_sop3 "l" 4.3 2.75 -0.50)
      (command "wedge" p_sop3 "l" -2.59 2.75 -0.50)
      (command "box" p_sop3 "l" 4.3 2.75 0.25)
      (command "box" p_sop3 "l" -2.59 2.75 0.25)
      (setq p_escalera1 (list (- (NTH 0 p_sop3) 2.59) (+ (NTH 1 p_sop3) 1.125) (+ (NTH 2 p_sop3) 0.25)))
      (setq p_escalera2 (list (NTH 0 p_escalera1) (+ (NTH 1 p_escalera1) 0.5) (NTH 2 p_escalera1)))
      (command "cylinder" p_escalera1 0.05 (* alt -1))
      (command "cylinder" p_escalera2 0.05 (* alt -1))
      (setq p_escalon (list (- (NTH 0 p_escalera1) 0.025) (+ (NTH 1 p_escalera1) 0.05) (- (NTH 2 p_escalera1) 0.25)))
      (command "box" p_escalon "l" 0.04 0.4 -0.02)
      (command "ucs" "x" "90")
      (command "array" (entlast) "" "r" (- (/ (* alt 100) 25) 1) 1 -0.25)
      (command "ucs" "w")

      ;barandas
      (command "layer" "m" "nueva3" "" "")
      (setq p_baranda1 (list (NTH 0 p_sop3) (+ (NTH 1 p_sop3) 0.05) (+ (NTH 2 p_sop3) 0.25)))
      (setq p_baranda2 (list (- (NTH 0 p_baranda1) 2.54) (NTH 1 p_baranda1) (NTH 2 p_baranda1)))
      (command "cylinder" p_baranda1 0.05 1)
      (setq prim_cil (entlast))
      (command "cylinder" p_baranda2 0.05 1)

      (setq p_sep_1 (list (NTH 0 p_baranda1) (NTH 1 p_baranda1) (+ (NTH 2 p_baranda1) 0.95)))
      (setq p_sep_2 (list (NTH 0 p_baranda2) (NTH 1 p_baranda2) (+ (NTH 2 p_baranda2) 0.95)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")

      (setq p_cil (list (NTH 0 p_baranda2) (+ (NTH 1 p_baranda2) 0.825) (NTH 2 p_baranda2)))
      (command "cylinder" p_cil 0.05 1)
      (setq p_sep_1 (list (NTH 0 p_cil) (NTH 1 p_cil) (+ (NTH 2 p_cil) 0.95)))
      (setq p_sep_2 (list (NTH 0 p_sep_1) (- (NTH 1 p_sep_1) 0.825) (NTH 2 p_sep_1)))
      (setq p_sep_3 (list (NTH 0 p_sep_2) (NTH 1 p_sep_2) (+ (NTH 2 p_sep_2) 0.05)))
      (setq p_sep_4 (list (NTH 0 p_sep_1) (NTH 1 p_sep_1) (+ (NTH 2 p_sep_1) 0.05)))
      (command "3dpoly" p_sep_1 p_sep_2 p_sep_3 p_sep_4 "c")
      (command "revolve" (entlast) "" p_sep_1 p_sep_2 "")
      
      (setq punmirr1 (list (NTH 0 p_sop3) (+ (NTH 1 p_sop3) 1.375) (NTH 2 p_sop3)))
      (setq punmirr2 (list (- (NTH 0 punmirr1) 2.59) (NTH 1 punmirr1) (NTH 2 punmirr1)))
      (setq enti (ssget "x" '((8 . "nueva3"))))
      (command "mirror" enti "" punmirr1 punmirr2 "")
      (setq enti1 (ssget "x" '((8 . "nueva3"))))
      (command "change" enti1 "" "p" "la" "0" "")
      (command "-layer" "set" "0" "")

      ;tramp_extras
      (if (= resp "si")
	(progn
	  (setq pbox (list (- (NTH 0 p_in) 2.5) (- (+ (NTH 1 p_in) (- lado (/ (/ lado 2) 2))) 2.5) (+ (NTH 2 p_in) prof)))
	  (command "box" pbox "l" 2.5 6 0.75)
	  (setq pboxaux (list (NTH 0 pbox) (+ (NTH 1 pbox) 0.1) (NTH 2 pbox)))
	  (command "layer" "m" "tramp_chico" "" "")
	  (command "box" pboxaux "l" -0.25 0.5 0.5)
	  (setq pbox2 (list (- (NTH 0 pboxaux) 0.25) (NTH 1 pboxaux) (NTH 2 pboxaux)))
	  (command "box" pbox2 "l" -0.25 0.5 0.25)
	  (setq pbar1 (list (+ (NTH 0 pbox) 0.05) (+ (NTH 1 pbox) 0.05) (+ (NTH 2 pbox) 0.75)))
	  (setq pbar2 (list (+ (NTH 0 pbar1) 2.4) (NTH 1 pbar1) (NTH 2 pbar1)))
	  (command "cylinder" pbar1 0.05 1)
	  (command "cylinder" pbar2 0.05 1)
	  (setq p1 (list (NTH 0 pbar1) (NTH 1 pbar1) (+ (NTH 2 pbar1) 0.95)))
	  (setq p2 (list (NTH 0 pbar2) (NTH 1 pbar2) (+ (NTH 2 pbar2) 0.95)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_cil1 (list (+ (NTH 0 pbox) 1.3) (+ (NTH 1 pbox) 1.2) (+ (NTH 2 pbox) 0.75)))
	  (setq p_cil2 (list (NTH 0 p_cil1) (+ (NTH 1 p_cil1) 0.6) (NTH 2 p_cil1)))
	  (command "cylinder" p_cil1 0.05 0.15)
	  (command "cylinder" p_cil2 0.05 0.15)
	  (setq p_circ1 (list (NTH 0 p_cil1) (NTH 1 p_cil1) (+ (NTH 2 p_cil1) 0.15)))
	  (setq p_circ2 (list (NTH 0 p_cil2) (NTH 1 p_cil2) (+ (NTH 2 p_cil2) 0.15)))
	  (command "circle" p_circ1 0.05)
	  (setq cir1 (entlast))
	  (command "circle" p_circ2 0.05)
	  (setq cir2 (entlast))
	  (setq p_rev1 (list (NTH 0 p_circ1) (+ (NTH 1 p_circ1) 0.05) (NTH 2 p_circ1)))
	  (setq p_rev2 (list (- (NTH 0 p_rev1) 0.1) (NTH 1 p_rev1) (NTH 2 p_rev1)))
	  (setq p_rev11 (list (NTH 0 p_circ2) (- (NTH 1 p_circ2) 0.05) (NTH 2 p_circ2)))
	  (setq p_rev22 (list (- (NTH 0 p_rev11) 0.1) (NTH 1 p_rev11) (NTH 2 p_rev11)))
	  (command "revolve" cir1 "" p_rev1 p_rev2 90)
	  (command "revolve" cir2 "" p_rev11 p_rev22 -90)
	  (setq p1 (list (NTH 0 p_cil1) (+ (NTH 1 p_cil1) 0.05) (+ (NTH 2 p_cil1) 0.2)))
	  (setq p2 (list (NTH 0 p1) (+ (NTH 1 p1) 0.5) (NTH 2 p1)))
	  (setq p3 (list (NTH 0 p2) (NTH 1 p2) (+ (NTH 2 p2) 0.05)))
	  (setq p4 (list (NTH 0 p1) (NTH 1 p1) (+ (NTH 2 p1) 0.05)))
	  (command "3dpoly" p1 p2 p3 p4 "c")
	  (command "revolve" (entlast) "" p1 p2 360)
	  (setq p_tramp (list (NTH 0 p1) (NTH 1 p1) (+ (NTH 2 p1) 0.05)))
	  (command "box" p_tramp "l" 3 0.5 0.05)
	  (setq p_boxtramp (list (+ (NTH 0 p_tramp) 0.6) (+ (NTH 1 p_tramp) 0.05) (NTH 2 p_tramp)))
	  (command "box" p_boxtramp "l" 0.4 0.4 -0.25)
	  (setq pmirr1 (list (+ (NTH 0 pbox) 2.5) (+ (NTH 1 pbox) 3) (+ (NTH 2 pbox) 0.75)))
	  (setq pmirr2 (list (- (NTH 0 pmirr1) 2.5) (NTH 1 pmirr1) (NTH 2 pmirr1)))
	  (setq enti (ssget "x" '((8 . "tramp_chico"))))
	  (command "mirror" enti "" pmirr1 pmirr2 "")
	  (setq enti1 (ssget "x" '((8 . "tramp_chico"))))
	  (command "change" enti1 "" "p" "la" "0" "")
	  (command "-layer" "set" "0" "")
	  )
	)

      ;ESCALERAS
      (command "-layer" "n" "escaleras" "set" "escaleras" "")
      (command "ucs" "w")
      ;definir punto de inicio escalera
      (setq p0 (list (+ (nth 0 p_in) 0.3) (+ (nth 1 p_in) (+ lado 0.3)) (+ (nth 2 p_in) prof)));punto inicio de la escalera
      ;cilindro 1
      (command "cylinder" p0 0.02 0.45)
      (setq cilindro1 (entlast))
      ;cilindro curvo 1
      (command "zoom" "e")
      (setq p1 (list (nth 0 p0) (nth 1 p0) (+(nth 2 p0)0.45) ))
      (command "circle" p1 0.02 "")
      (setq circulo1 (entlast))
      (setq p1Eje (list (nth 0 p1) (- (nth 1 p1) 0.3) (nth 2 p1) ))
      (setq p2Eje (list (- (nth 0 p1) 0.3) (- (nth 1 p1) 0.3) (nth 2 p1)))
      (command "revolve" circulo1 "" p1Eje p2Eje -180 "")
      (setq cilindroCurvo (entlast))
      ;cilindro 2
      (setq p2 (list (nth 0 p1) (-(nth 1 p1)0.60) (nth 2 p1)))
      (command "cylinder" p2 0.02 -1.45)
      (setq cilindro2 (entlast))
      ;cilindro curvo 2
      (setq p3 (list (nth 0 p2) (nth 1 p2) (-(nth 2 p2) 1.45)))
      (command "circle" p3 0.02 "")
      (setq circulo2 (entlast))
      (setq p1Eje2 (list (nth 0 p3) (+ (nth 1 p3) 0.3) (nth 2 p3)))
      (setq p2Eje2 (list (+ (nth 0 p3) 0.3) (+ (nth 1 p3) 0.3) (nth 2 p3)))
      (command "revolve" circulo2 "" p1Eje2 p2Eje2 90 "")
      (setq cilindroCurvo2 (entlast))
      (command "union"  cilindro1 cilindroCurvo cilindro2 cilindroCurvo2 "")
      (setq canio1 (entlast))
      ;caño dos
      (setq p0Canio2 (list (+ (nth 0 p0) 0.5) (nth 1 p0)(nth 2 p0)))
      (command "copy" canio1 "" p0  p0Canio2)
      ;escalones
      (setq p1Escalon (list (nth 0 p2) (-(nth 1 p2) 0.075) (-(nth 2 p2)0.65)));
      (command "box" p1Escalon "l" 0.5 0.15 -0.03)
      (setq escalon (entlast))
      (command "ucs" "x" 90)
      (command "array" escalon "" "r" 4 1 -0.25)
      (command "ucs" "w")
      (command "-layer" "set" "escaleras" "")
      (setq escaleraTodo (ssget "x" '((8 . "escaleras"))))
      (command "union" escaleraTodo "" )
      (setq escComp (entlast));escalera
      ;escalera 2
      (command "zoom" "e")
      (setq mir1 (list (+ (NTH 0 p_in) (/ lado 2)) (NTH 1 p_in) (NTH 2 p_in)))
      (setq mir2 (list (NTH 0 mir1) (+ (NTH 1 mir1) lado) (NTH 2 mir1)))
      (command "mirror" escComp "" mir1 mir2 "")
      (setq escComp2 (entlast))
      ;miror
      (setq mi1l (list (+ (NTH 0 p_in) lado) (+ (NTH 1 p_in) (/ lado 2)) (NTH 2 p_in)))
      (setq mi2l (list (- (NTH 0 mi1l) lado) (NTH 1 mi1l) (NTH 2 mi1l)))
      (command "mirror" escComp escComp2 "" mi1l mi2l "")
      (setq enti1 (ssget "x" '((8 . "escaleras"))))
      (command "change" enti1 "" "p" "la" "0" "")
      (command "-layer" "set" "0" "")

      ;seeparador
      (command "layer" "m" "nueva" "" "")
      (setq radio_sep (/ diametro_separador 2))
      (setq numbloc1 (fix (/ (/ lado 4) diametro_separador))
	    numbloc2 (fix (/ (/ lado 2) diametro_separador)))
      (setq pun_separador1 (list (+ (NTH 0 p_in) (/ (* lado 80) 100)) (+ (NTH 1 p_in) radio_sep) (+ (NTH 2 p_in) (- prof 0.1))))
      (setq p_sep_1 (list (NTH 0 pun_separador1) (- (NTH 1 pun_separador1) radio_sep) (- (NTH 2 pun_separador1) 0.01)))
      (setq p_sep_2 (list (NTH 0 p_sep_1) (+ (NTH 1 p_sep_1) lado) (NTH 2 p_sep_1)))
      (setq p_sep_3 (list (NTH 0 p_sep_2) (NTH 1 p_sep_2) (+ (NTH 2 p_sep_2) 0.02)))
      (setq p_sep_4 (list (NTH 0 p_sep_1) (NTH 1 p_sep_1) (+ (NTH 2 p_sep_1) 0.02)))
      (command "3dpoly" p_sep_1 p_sep_2 p_sep_3 p_sep_4 "c")
      (command "revolve" (entlast) "" p_sep_1 p_sep_2 "")
      (command "_color" 2)
      (command "sphere" pun_separador1 radio_sep)
      (command "array" (entlast) "" "r" numbloc1 1 diametro_separador)
      (setq pun_separador2 (list (NTH 0 pun_separador1) (+ (NTH 1 pun_separador1) (/ lado 4)) (NTH 2 pun_separador1)))
      (command "_color" 1)
      (command "sphere" pun_separador2 radio_sep)
      (command "array" (entlast) "" "r" numbloc2 1 diametro_separador)
      (setq pun_separador3 (list (NTH 0 pun_separador2) (+ (NTH 1 pun_separador2) (/ lado 2)) (NTH 2 pun_separador2)))
      (command "_color" 2)
      (command "sphere" pun_separador3 radio_sep)
      (command "array" (entlast) "" "r" numbloc1 1 diametro_separador)
      (setq enti1 (ssget "x" '((8 . "nueva"))))
      (command "change" enti1 "" "p" "la" "0" "")
      (command "-layer" "set" "0" "")
      ;luces
      (command "-layer" "set" "0" "")
      (if (<= lado 16)
	(progn
	  (command "_color" 7)
	  (setq punto_luz (list (+ (NTH 0 p_in) (/ lado 3)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 2 (/ lado 3))))
      (if (>= lado 17)
	(progn
	  (command "_color" 7)
	  (setq punto_luz (list (+ (NTH 0 p_in) (/ lado 4)) (- (NTH 1 p_in) 0.025) (+ (NTH 2 p_in) (/ (* 75 prof) 100))))
	  (command "sphere" punto_luz 0.125)
	  (setq prim (entlast))
	  (setq punmirr1 (list (NTH 0 p_in) (+ (NTH 1 p_in) (/ lado 2)) (NTH 2 p_in)))
	  (setq punmirr2 (list (+ (NTH 0 punmirr1) lado) (NTH 1 punmirr1) (NTH 2 punmirr1)))
	  (command "mirror" (entlast) "" punmirr1 punmirr2 "")
	  (command "array" prim (entlast) "" "r" 1 3 (/ lado 4))))
      (command "-layer" "set" "0" "")
      (command "union" "all" "")
      (command "regen")
      (command "purge" "all" "" "n")
      (command "hide")
      ))
)

(defun pilesemi()
  (setq pin (getpoint "\nIngrese el punto base de la pileta: "))
  (setq anchoCarril (getreal "\nIngrese el ancho de los carriles (entre 2 mts o 2.5 mts): "))
  (while (and (/= anchoCarril 2) (/= anchoCarril 2.5))
    (setq anchoCarril (getreal "\nIngrese el ancho de los carriles (entre 2 mts o 2.5 mts): "))
  )
  (setq	ancho_borde (getreal "\nIngrese el ancho del borde de la pileta (entre 0.5 mts y 1 mts): "))
  (while (or (> ancho_borde 1) (< ancho_borde 0.5))
    (setq ancho_borde (getreal "\nIngrese el ancho del borde de la pileta (entre 0.5 mts y 1 mts): "))
  )
  (setq profundidadPileta (getreal "\nIngrese la profudidad de la pileta (entre 1.8 mts y 2 mts: "))
  (while (or (> profundidadPileta 2) (< profundidadPileta 1.8))
    (setq profundidadPileta (getreal "\nIngrese la profudidad de la pileta (entre 1.8 mts y 2 mts: "))
   )
  
;HUECO DE LA PILETA
  (command "-layer" "set" "0" "")
  (setq anchoPileta 12.5) 		 ;ver como variar
            ; (setq profPileta 2.1) 		 
  (setq profPileta (+ profundidadPileta 0.30 ));profundidad pileta CONSIDERANDO EL ALTO 0.30 DE LAS VEREDAS 
  (setq ancho_final (+ anchoPileta 0.30))     ;ancho del segundo box para hacer las paredes
  (command "_color" 4)
  (command "box" pin "l" 25 anchoPileta profPileta)
  (setq hueco_pileta (entlast))
  (setq pInExt (list (- (NTH 0 pin) 0.15) (- (NTH 1 pin) 0.15) (- (NTH 2 pin) 0.15)));punto inicial box 2
  (setq prof_final (+ profPileta 0.15))			 ;profundidad con las paredes de 0.15cm
  (command "box" pInExt "l" 25.30 ancho_final prof_final);altura=profPileta + 0.15=2.5  2.25
  (command "subtract" (entlast) "" hueco_pileta "")
  (setq pileta (entlast));pileta con hueco

;SUAVIZADO
  (command "zoom" "e")
  (command "_color" 4)
  ;suavizado de bordes laterales
  (setq p7 (list (nth 0 pin) (nth 1 pin) (+(nth 2 pin)(/ profPileta 2)) ))
  (command "fillet" p7 0.25 "")
  (setq p8 (list (+ (nth 0 pin) 25) (nth 1 pin) (+(nth 2 pin)(/ profPileta 2)) ))
  (command "fillet" p8 0.25 "")
  (setq p9 (list (+ (nth 0 pin) 25) (+ (nth 1 pin) anchoPileta) (+(nth 2 pin)(/ profPileta 2)) ))
  (command "fillet" p9 0.25 "")
  (setq p10 (list (nth 0 pin) (+ (nth 1 pin) anchoPileta) (+(nth 2 pin)(/ profPileta 2)) ))
  (command "fillet" p10 0.25 "")
  ;defino 4 puntos para hacer fillet bordes inferior
  (setq p3(list (NTH 0 pin) (+ (NTH 1 pin) (/ anchoPileta 2)) (NTH 2 pin)))
  (command "fillet" p3 0.25 "")
  (setq p4(list (+ (NTH 0 pin) anchoPileta) (NTH 1 pin)  (NTH 2 pin)))
  (command "fillet" p4 0.25 "")
  (setq p5 (list (+(nth 0 pin) 25) (+ (NTH 1 pin) (/ anchoPileta 2)) (NTH 2 pin)))
  (command "fillet" p5 0.25 "")
  (setq p6 (list (+ (NTH 0 pin) anchoPileta) (+ (NTH 1 pin) anchoPileta) (NTH 2 pin)))
  (command "fillet" p6 0.25 "")

;ACERAS 
  (command "_color" 8)
  (setq p1 (list (-(nth 0 pin) ancho_borde) (-(nth 1 pin) ancho_borde) (+(NTH 2 pin) profPileta)))
  (command "box" p1 "l" (+ 25 (* 2 ancho_borde)) (+ 12.5 (* 2 ancho_borde)) -0.15)
  (setq vereda (entlast))
  (setq p2 (list (- (nth 0 pin) 0.15) (- (nth 1 pin) 0.15) (+(NTH 2 pin) profPileta) ));box 2 CONSIDERA LAS PAREDES
  (command "box" p2 "l" 25.3 12.8 -0.15);CONSIDERANDO LAS PAREDES 
  (command "subtract" vereda "" (entlast) "")


  
;BANDERINES
  (command "-layer" "n" "banderines" "set" "banderines" "")
  (command "-color" 255)
  (setq p1b(list (+(nth 0 pin) 5) (-(nth 1 pin)0.20) (+(nth 2 pin) profPileta)))
  (command "cylinder" p1b 0.05 1.8);cilindro 1 pie banderin 
  (setq separacion (+ anchoPileta (* 2 0.20)))
  (setq p2b(list (nth 0 p1b) (+ (nth 1 p1b) separacion) (nth 2 p1b)))
  (command "cylinder" p2b 0.05 1.8);cilindro 2 pie banderin
  ;cuerda
  (setq pcuerda1 (list (nth 0 p1b) (nth 1 p1b) (+(nth 2 p1b) 1.80))) 
  (command "ucs" "x" "90")
  ;(setq pAux (list (nth 0 p1b) (+(nth 2 p1b)1.80) (+(nth 1 p1b)0.40)));punto base del cilindro que es la cuerda
  (setq pAux(trans pcuerda1 0 1));+++++++++++++++++++++++++++++++++++++++++++++++++++++++++++++++
  (command "cylinder" pAux 0.0005 -12.9)
  (command "ucs" "W")
  ;dibujo del banderin
  (command "_color" 50)
  (setq 1pb (list (nth 0 pcuerda1) (+(nth 1 pcuerda1)0.15) (nth 2 pcuerda1)))
  (setq 2pb (list (nth 0 1pb) (+(nth 1 1pb)0.30) (nth 2 1pb)))
  (setq 3pb (list (nth 0 1pb) (+(nth 1 1pb)0.15) (-(nth 2 1pb)0.30) ))
  (command "_3dpoly" 1pb 2pb 3pb "c")
  (command "extrude" (entlast) "" 0.001 "")
  (setq banderin1 (entlast))
  (setq nroBanderines (/ separacion 0.30))
  (command "array" banderin1 "" "r" 42 1 0.30)
  (command "-layer" "set" "banderines" "")
  (setq todoCB (ssget "x" '((8 . "banderines"))))
  (command "union" todoCB "");banderines con cuerda y pies
  (setq banderin2 (entlast))
  (setq pfb(list (+(nth 0 p1b) 15) (nth 1 p1b) (nth 2 p1b)))
  (command "copy" banderin2 "" p1b pfb "")
  
;CUERDA SALIDA EN FALSO a 10 metros de la salida
  (command "_color" 255)
  (setq p1CSF(list (+(nth 0 pin) 10) (-(nth 1 pin)0.20) (+(nth 2 pin) profPileta))) ;punto base para el cilindro 1 pie cuerda salida en falso
  (command "cylinder" p1CSF 0.05 1.80) ;cilindro 1 pie cuerda salida en falso
  (setq cilindro1 (entlast))
  (setq p2CSF(list (nth 0 p1CSF) (+ (nth 1 p1CSF) separacion) (nth 2 p1CSF)))
  (command "cylinder" p2CSF 0.05 1.80);cilindro 1 pie banderin
  (setq cilindro2 (entlast))
  ;cuerda salida en falso 
  (setq pbCilindroCSF (list (nth 0 p1CSF) (nth 1 p1CSF) (+(nth 2 p1CSF)1.80) ));punto base del cilindro que es la cuerda 
  (command "ucs" "x" "90")
  (setq pAux2 (trans  pbCilindroCSF 0 1))
  (command "cylinder" pAux2 0.005 -12.9)
  (setq cuerda (entlast))
  (command "union" cilindro1 cilindro2 cuerda "")
  (setq cuerdaSalidaEnFalso (entlast))
  (command "ucs" "W")
  (command "-layer" "set" "0" "")

;LUCES
  (command "-layer" "n" "luces" "set" "luces" "") 
  (command "_color" 7)
  (setq punto_luz (list (+ (NTH 0 pin) 5) (- (NTH 1 pin) 0.025) (+ (NTH 2 pin) (- 1.8 (* 18 0.0254)))));(rever la altura)
  (command "sphere" punto_luz 0.125)
  (setq prim (entlast))
  (setq mi1l (list (NTH 0 pin) (+ (NTH 1 pin) 6.25) (+(NTH 2 pin)1) ))
  (setq mi2l (list (+ (NTH 0 pin) 25) (+ (NTH 1 pin) 6.25) (+(NTH 2 pin)1) ))
  (command "mirror" (entlast) "" mi1l mi2l "")
  (setq prim2 (entlast))
  (command "array" prim (entlast) "" "r" 1 4 5)

;MARCAS CARRILES
  (command "-layer" "set" "0" "")
  ;marcas carriles del piso 
  (command "_color" 251)
  (setq pm0 (list (+(nth 0 pin) 2) (+(nth 1 pin)0.875) (nth 2 pin)))
  (setq pm1 (list (+(nth 0 pm0) 0.25) (nth 1 pm0) (nth 2 pm0) ))
  (setq pm2 (list (nth 0 pm1) (+(nth 1 pm1)0.25) (nth 2 pm1)))
  (setq pm3 (list (+(nth 0 pm2) 20.5) (nth 1 pm2) (nth 2 pm2)))
  (setq pm4 (list (nth 0 pm3) (-(nth 1 pm3) 0.25) (nth 2 pm3)))
  (setq pm5 (list (+ (nth 0 pm4) 0.25) (nth 1 pm4) (nth 2 pm4)))
  (setq pm6 (list (nth 0 pm5) (+(nth 1 pm5) 0.75) (nth 2 pm5)))
  (setq pm7 (list (-(nth 0 pm6)0.25) (nth 1 pm6) (nth 2 pm6)))
  (setq pm8 (list (nth 0 pm7) (-(nth 1 pm7)0.25) (nth 2 pm7)))
  (setq pm9 (list (-(nth 0 pm8)20.5) (nth 1 pm8) (nth 2 pm8)))
  (setq pm10 (list (nth 0 pm9) (+(nth 1 pm9)0.25) (nth 2 pm9)))
  (setq pm11 (list (-(nth 0 pm10)0.25) (nth 1 pm10) (nth 2 pm10)))
  (command "pline" pm0 pm1 pm2 pm3 pm4 pm5 pm6 pm7 pm8 pm9 pm10 pm11 "c")
  (command "extrude" (entlast) "" 0.001 "")
  (setq marcaPiso (entlast)) 
  (if (= anchoCarril 2.5)
	(command "array" (entlast) "" "r" 5 1 2.5)
  )
  (if (= anchoCarril 2) 
    (progn
    (setq pmNuevo (list (+ (nth 0 pin) 2) (+ (nth 1 pin) 0.625) (nth 2 pin)))
    (command "move" marcaPiso "" pm0 pmNuevo) 
    (command "array" (entlast) "" "r" 6 1 2)
    )
  )
  ;marcas carriles de la pared
  (setq alturaAux (- profundidadPileta 0.60))
  (setq mp0 (list (-(nth 0 pm2) 2.25) (nth 1 pm2)(nth 2 pm2)))
  (setq mp1 (list (nth 0 mp0) (nth 1 mp0) (+ (nth 2 mp0) alturaAux)));       
  (setq mp2 (list (nth 0 mp1) (-(nth 1 mp1)0.25) (nth 2 mp1)))
  (setq mp3 (list (nth 0 mp2) (nth 1 mp2) (+ (nth 2 mp2) 0.25)))
  (setq mp4 (list (nth 0 mp3) (+ (nth 1 mp3)0.25) (nth 2 mp3)))
  (setq mp5 (list (nth 0 mp4) (nth 1 mp4) (+ (nth 2 mp4) 0.25)))
  (setq mp6 (list (nth 0 mp5) (+ (nth 1 mp5)0.25) (nth 2 mp5)))
  (setq mp7 (list (nth 0 mp6) (nth 1 mp6) (- (nth 2 mp6) 0.25)))
  (setq mp8 (list (nth 0 mp7) (+ (nth 1 mp7)0.25) (nth 2 mp7)))
  (setq mp9 (list (nth 0 mp8) (nth 1 mp8) (- (nth 2 mp8) 0.25)))
  (setq mp10 (list (nth 0 mp9) (- (nth 1 mp9)0.25) (nth 2 mp9)))
  (setq mp11 (list (nth 0 mp10) (nth 1 mp10) (- (nth 2 mp10) alturaAux)));            
  (command "_3dpoly" mp0 mp1 mp2 mp3 mp4 mp5 mp6 mp7 mp8 mp9 mp10 mp11 "c")
  (command "extrude" (entlast) "" 0.001 "")
  (setq form1 (entlast))
  ;dos puntos para hacer el mirror
  (setq mi1 (list (+ (NTH 0 pin) 12.5) (NTH 1 pin) (NTH 2 pin)))
  (setq mi2 (list (+ (NTH 0 pin) 12.5) (+ (NTH 1 pin) anchoPileta) (NTH 2 pin)))
  (command "mirror" (entlast) "" mi1 mi2 "")
  (setq form2 (entlast))
  (if (= anchoCarril 2.5) 
   (command "array" form1 form2 "" "r" 5 1 2.5)	 
  )
  (if (= anchoCarril 2)
    (progn
      (setq pmParedNuevo (list (nth 0 mp0) (-(nth 1 mp0)0.25) (nth 2 mp0)))
      (command "move" form1 form2 "" mp0 pmParedNuevo)
      (command "array" form1 form2 "" "r" 6 1 2)
  ))

;SEPARADORES DE CARRILES ESFERAS
  ;cilindro cuerda ESFERAS
  (command "-layer" "n" "esferas" "set" "esferas" "")
  (setq radioEsfera 0.05)
  ;                                                                                                                              
  (setq pe0 (list (+ (nth 0 pin) radioEsfera) (+ (nth 1 pin) 2.5) (+(nth 2 pin) profundidadPileta)));cambiar la coordenada en z va mas abajo
  (setq pe1 (list (+ (nth 0 pe0) 5) (nth 1 pe0) (nth 2 pe0) ))
  (setq pe2 (list (+ (nth 0 pe1) 15) (nth 1 pe1) (nth 2 pe1) ))
  (command "_color" 50)
  (command "sphere" pe0 radioEsfera "")   
  (command "array" (entlast) "" "r" 1 50 0.1)                                            
  (command "_color" 10)
  (command "sphere" pe1 radioEsfera "")
  (command "array" (entlast) "" "r" 1 150 0.1)
  (command "_color" 50)
  (command "sphere" pe2 radioEsfera "")
  (command "array" (entlast) "" "r" 1 50 0.1)
  (command "-layer" "set" "esferas" "")

  (command "_color" 251)
  (setq pbccE (list  (nth 0 pin) (+ (nth 1 pin) 2.5) (+(nth 2 pin) profundidadPileta)))
  (command "ucs" "y" "-90")
  ;(setq p0CilindroCuerdaEsferas (list (+(nth 2 pin) profundidadPileta) (+ (nth 1 pin) 2.5)(nth 0 pin)))
  (setq p0CilindroCuerdaEsferas (trans pbccE 0 1))
  (command "cylinder" p0CilindroCuerdaEsferas 0.025 -25)
  (command "ucs" "W")
  (setq esferitas (ssget "x" '((8 . "esferas")) ))
  (command "union" esferitas "")
  (setq carrilEsferas (entlast))
  (command "-layer" "set" "0" "")
  (if (= anchoCarril 2.5) ;si el ancho es el maximo, agrega las marcas del fondo del carril
   (command "array" carrilEsferas "" "r" 4 1 2.5)	 
  )
  (if (= anchoCarril 2)
    (progn
      (setq nuevopunto (list (nth 0 pe0) (- (nth 1 pe0) 0.5) (nth 2 pe0)));0.25
      (command "move" carrilEsferas "" pe0 nuevopunto)
      (command "array" carrilEsferas "" "r" 5 1 2)
   ))
  

;ESCALERAS
  (command "_color" 9)
  (command "-layer" "n" "escaleras" "set" "escaleras" "")
  (command "ucs" "w")
  ;definir punto de inicio escalera
  (setq p0 (list (+ (nth 0 pin)0.3) (+ (nth 1 pin) 12.85) (+ (nth 2 pin) profPileta) ));punto inicio de la escalera                                                               
  ;cilindro 1
  (command "cylinder" p0 0.02 0.45)
  (setq cilindro1 (entlast))
  ;cilindro curvo 1
  (command "zoom" "e")
  (setq p1 (list (nth 0 p0) (nth 1 p0) (+(nth 2 p0)0.45) ))
  (command "circle" p1 0.02 "")
  (setq circulo1 (entlast))
  (setq p1Eje (list (nth 0 p1) (- (nth 1 p1) 0.3) (nth 2 p1) ))
  (setq p2Eje (list (- (nth 0 p1) 0.3) (- (nth 1 p1) 0.3) (nth 2 p1)))
  (command "revolve" circulo1 "" p1Eje p2Eje -180 "")
  (setq cilindroCurvo (entlast))
  ;cilindro 2
  (setq p2 (list (nth 0 p1) (-(nth 1 p1)0.60) (nth 2 p1)))
  (command "cylinder" p2 0.02 -1.45)
  (setq cilindro2 (entlast))
  ;cilindro curvo 2
  (setq p3 (list (nth 0 p2) (nth 1 p2) (-(nth 2 p2) 1.45)))
  (command "circle" p3 0.02 "")
  (setq circulo2 (entlast))
  (setq p1Eje2 (list (nth 0 p3) (+ (nth 1 p3) 0.3) (nth 2 p3)))
  (setq p2Eje2 (list (+ (nth 0 p3) 0.3) (+ (nth 1 p3) 0.3) (nth 2 p3)))
  (command "revolve" circulo2 "" p1Eje2 p2Eje2 90 "")
  (setq cilindroCurvo2 (entlast))
  (command "union"  cilindro1 cilindroCurvo cilindro2 cilindroCurvo2 "")
  (setq canio1 (entlast))
  ;caño dos
  (setq p0Canio2 (list (+ (nth 0 p0) 0.5) (nth 1 p0)(nth 2 p0)))
  (command "copy" canio1 "" p0  p0Canio2)
  ;escalones
  (setq p1Escalon (list (nth 0 p2) (-(nth 1 p2) 0.075) (-(nth 2 p2)0.65)));              
  (command "box" p1Escalon "l" 0.5 0.15 -0.03)
  (setq escalon (entlast))
  (command "ucs" "x" 90)
  (command "array" escalon "" "r" 4 1 -0.25)
  (command "ucs" "w")
  (command "-layer" "set" "escaleras" "")
  (setq escaleraTodo (ssget "x" '((8 . "escaleras"))))
  (command "union" escaleraTodo "" )
  (setq escComp (entlast));escalera 1
;escalera 2
  (command "zoom" "e")
  (setq piEscalera2 (list (+(nth 0 p0) 23.9) (nth 1 p0) (nth 2 p0)))
  (command "copy" escComp "" p0 piEscalera2)
  (setq escComp2 (entlast))
  ;miror
  ;(setq mi1l (list (NTH 0 pin) (+ (NTH 1 pin) 6.25) (+(NTH 2 pin)1) ))
  ;(setq mi2l (list (+ (NTH 0 pin) 25) (+ (NTH 1 pin) 6.25) (+(NTH 2 pin)1) ))
  (command "mirror" escComp escComp2 "" mi1l mi2l "")

  ; TIRADOR
  ;la altura de la inclinacion es c, inclinacion gama y la base es a. tang gama = c/a, de ahi despejo la altura
  (command "-layer" "set" "0" "")
  (command "_color" 251)
  (setq altura 0.5)
  (setq pun_tir (list (- (NTH 0 pin) 0.5) (+ (NTH 1 pin) 1) (+ (+ (NTH 2 pin) profPileta) altura)))
  (setq angulo_rad (/ (* 10 (* 2 pi)) 360));podria variar el angulo gama=10 
  (setq altura_inclinacion (* (/ (sin angulo_rad)(cos angulo_rad)) 0.5))
  (command "box" pun_tir "l" 0.5 0.5 (/ (* 25 altura) 100))
  (setq box_inf (entlast))
  (setq punto_aux (list (NTH 0 pun_tir) (NTH 1 pun_tir) (+ (NTH 2 pun_tir) (/ (* 25 altura) 100))))
  (command "wedge" punto_aux "l" 0.5 0.5 altura_inclinacion)
  (setq box_sup (entlast))
  (setq punto_aux (list (+ (NTH 0 pun_tir) 0.25) (+ (NTH 1 pun_tir) 0.25) (NTH 2 pun_tir)))
  (command "cylinder" punto_aux 0.1 (* -1 altura))
  ;(command "cylinder" punto_aux 0.1 (* (- altura 0.3) -1))
  (command "union" box_inf box_sup (entlast) "")
  (setq tirador (entlast))
  (if (= anchoCarril 2.5) ;si el ancho es el maximo, agrega las marcas del fondo del carril
     (command "array" tirador "" "r" 5 1 2.5)
  )
  (if (= anchoCarril 2)
    (progn
      (setq ptirador (list (nth 0 punto_aux) (- (nth 1 punto_aux) 0.25) (nth 2 punto_aux)))
      (command "move" tirador "" punto_aux ptirador)
      (command "array" tirador "" "r" 6 1 2)
   ))

  
(command "-layer" "set" "0" "")  
(COMMAND "UNION" "ALL" "")
(COMMAND "REGEN")
(command "purge" "all" "" "n")
(COMMAND "hide")
 
)
